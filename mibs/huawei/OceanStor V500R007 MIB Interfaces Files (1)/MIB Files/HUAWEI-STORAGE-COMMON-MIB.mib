--
-- HUAWEI-STORAGE-COMMON-MIB.mib
-- MIB generated by MG-SOFT Visual MIB Builder Version 4.0 Build 347
-- Saturday, February 24, 2018 at 10:23:25
--

	HUAWEI-STORAGE-COMMON-MIB DEFINITIONS ::= BEGIN
 
		IMPORTS
			enterprises, OBJECT-TYPE, MODULE-IDENTITY			
				FROM SNMPv2-SMI;
	
	
		storage MODULE-IDENTITY 
			LAST-UPDATED "201802241021Z"		-- February 24, 2018 at 10:21 GMT
			ORGANIZATION 
				"Organization."
			CONTACT-INFO 
				"Contact-info."
			DESCRIPTION 
				"The HUAWEI-STORAGE-COMMON-MIB contains objects of patch version."
			::= { products 251 }

		
	
--
-- Node definitions
--
	
		huawei OBJECT IDENTIFIER ::= { enterprises 2011 }

		
		products OBJECT IDENTIFIER ::= { huawei 2 }

		
		common OBJECT IDENTIFIER ::= { storage 1 }

		-- 1.3.6.1.4.1.2011.2.251.1.7
		patchversion OBJECT-TYPE
			SYNTAX OCTET STRING
			MAX-ACCESS read-write
			STATUS current
			DESCRIPTION
				"Patch version."
			::= { common 7 }

		
	
	END

--
-- HUAWEI-STORAGE-COMMON-MIB.mib
--
