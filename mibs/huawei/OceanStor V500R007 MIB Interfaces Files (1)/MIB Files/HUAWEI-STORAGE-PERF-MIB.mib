--
-- HUAWEI-STORAGE-PERF-MIB.mib
-- MIB generated by MG-SOFT Visual MIB Builder Version 6.0  Build 88
-- Thursday, April 13, 2017 at 16:16:34
--

	HUAWEI-STORAGE-PERF-MIB DEFINITIONS ::= BEGIN
 
		IMPORTS
			enterprises, Unsigned32, Counter64, OBJECT-TYPE			
				FROM SNMPv2-SMI;
	
	
--
-- Node definitions
--
	
		-- 1.3.6.1.4.1.2011
		huawei OBJECT IDENTIFIER ::= { enterprises 2011 }

		
		-- 1.3.6.1.4.1.2011.2
		products OBJECT IDENTIFIER ::= { huawei 2 }

		
		-- 1.3.6.1.4.1.2011.2.251
		storage OBJECT IDENTIFIER ::= { products 251 }

		
		-- 1.3.6.1.4.1.2011.2.251.21
		performance OBJECT IDENTIFIER ::= { storage 21 }

		
		-- 1.3.6.1.4.1.2011.2.251.21.10
		hwPerfDiskTable OBJECT-TYPE
			SYNTAX SEQUENCE OF HwPerfDiskEntry
			MAX-ACCESS not-accessible
			STATUS current
			DESCRIPTION
				"This table is used to query the performance of a disk."
			::= { performance 10 }

		
		-- 1.3.6.1.4.1.2011.2.251.21.10.1
		hwPerfDiskEntry OBJECT-TYPE
			SYNTAX HwPerfDiskEntry
			MAX-ACCESS not-accessible
			STATUS current
			DESCRIPTION
				"A table containing the part component."
			INDEX { hwPerfDiskIndex }
			::= { hwPerfDiskTable 1 }

		
		HwPerfDiskEntry ::=
			SEQUENCE { 
				hwPerfDiskIndex
					OCTET STRING,
				hwPerfDiskTotalIOPS
					Unsigned32,
				hwPerfDiskReadIOPS
					Unsigned32,
				hwPerfDiskWriteIOPS
					Unsigned32,
				hwPerfDiskTotalTraffic
					Counter64,
				hwPerfDiskReadTraffic
					Counter64,
				hwPerfDiskWriteTraffic
					Counter64,
				hwPerfDiskDelay
					Counter64,
				hwPerfDiskLengthOfQueue
					Unsigned32,
				hwPerfDiskAverageIO
					Unsigned32,
				hwPerfDiskAverageReadIO
					Unsigned32,
				hwPerfDiskAverageWriteIO
					Unsigned32,
				hwPerfDiskMaxIOPS
					Unsigned32
			 }

		-- 1.3.6.1.4.1.2011.2.251.21.10.1.1
		hwPerfDiskIndex OBJECT-TYPE
			SYNTAX OCTET STRING
			MAX-ACCESS read-only
			STATUS current
			DESCRIPTION
				"Disk ID."
			::= { hwPerfDiskEntry 1 }

		
		-- 1.3.6.1.4.1.2011.2.251.21.10.1.2
		hwPerfDiskTotalIOPS OBJECT-TYPE
			SYNTAX Unsigned32
			MAX-ACCESS read-only
			STATUS current
			DESCRIPTION
				"IOPS (unit: IO/s)."
			::= { hwPerfDiskEntry 2 }

		
		-- 1.3.6.1.4.1.2011.2.251.21.10.1.3
		hwPerfDiskReadIOPS OBJECT-TYPE
			SYNTAX Unsigned32
			MAX-ACCESS read-only
			STATUS current
			DESCRIPTION
				"Read IOPS (unit: IO/s)."
			::= { hwPerfDiskEntry 3 }

		
		-- 1.3.6.1.4.1.2011.2.251.21.10.1.4
		hwPerfDiskWriteIOPS OBJECT-TYPE
			SYNTAX Unsigned32
			MAX-ACCESS read-only
			STATUS current
			DESCRIPTION
				"Write IOPS (unit: IO/s)."
			::= { hwPerfDiskEntry 4 }

		
		-- 1.3.6.1.4.1.2011.2.251.21.10.1.5
		hwPerfDiskTotalTraffic OBJECT-TYPE
			SYNTAX Counter64
			MAX-ACCESS read-only
			STATUS current
			DESCRIPTION
				"Bandwidth (unit: MB/s)."
			::= { hwPerfDiskEntry 5 }

		
		-- 1.3.6.1.4.1.2011.2.251.21.10.1.6
		hwPerfDiskReadTraffic OBJECT-TYPE
			SYNTAX Counter64
			MAX-ACCESS read-only
			STATUS current
			DESCRIPTION
				"Read bandwidth (unit: MB/s)."
			::= { hwPerfDiskEntry 6 }

		
		-- 1.3.6.1.4.1.2011.2.251.21.10.1.7
		hwPerfDiskWriteTraffic OBJECT-TYPE
			SYNTAX Counter64
			MAX-ACCESS read-only
			STATUS current
			DESCRIPTION
				"Write bandwidth (unit: MB/s)."
			::= { hwPerfDiskEntry 7 }

		
		-- 1.3.6.1.4.1.2011.2.251.21.10.1.8
		hwPerfDiskDelay OBJECT-TYPE
			SYNTAX Counter64
			MAX-ACCESS read-only
			STATUS current
			DESCRIPTION
				"Response time (unit: μs)."
			::= { hwPerfDiskEntry 8 }

		
		-- 1.3.6.1.4.1.2011.2.251.21.10.1.9
		hwPerfDiskLengthOfQueue OBJECT-TYPE
			SYNTAX Unsigned32
			MAX-ACCESS read-only
			STATUS current
			DESCRIPTION
				"Queue length."
			::= { hwPerfDiskEntry 9 }

		
		-- 1.3.6.1.4.1.2011.2.251.21.10.1.11
		hwPerfDiskAverageIO OBJECT-TYPE
			SYNTAX Unsigned32
			MAX-ACCESS read-write
			STATUS current
			DESCRIPTION
				"Average I/O size (unit: KB)."
			::= { hwPerfDiskEntry 11 }

		
		-- 1.3.6.1.4.1.2011.2.251.21.10.1.12
		hwPerfDiskAverageReadIO OBJECT-TYPE
			SYNTAX Unsigned32
			MAX-ACCESS read-only
			STATUS current
			DESCRIPTION
				"Average read I/O size (unit: KB)."
			::= { hwPerfDiskEntry 12 }

		
		-- 1.3.6.1.4.1.2011.2.251.21.10.1.13
		hwPerfDiskAverageWriteIO OBJECT-TYPE
			SYNTAX Unsigned32
			MAX-ACCESS read-only
			STATUS current
			DESCRIPTION
				"Average write I/O size (unit: KB)."
			::= { hwPerfDiskEntry 13 }

		
		-- 1.3.6.1.4.1.2011.2.251.21.10.1.14
		hwPerfDiskMaxIOPS OBJECT-TYPE
			SYNTAX Unsigned32
			MAX-ACCESS read-only
			STATUS current
			DESCRIPTION
				"Maximum IOPS (unit: IO/s)."
			::= { hwPerfDiskEntry 14 }

		
	
	END

--
-- HUAWEI-STORAGE-PERF-MIB.mib
--
