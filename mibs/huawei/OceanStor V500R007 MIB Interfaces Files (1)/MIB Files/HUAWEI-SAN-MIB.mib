--
-- HUAWEI-SAN-MIB.mib
-- MIB generated by MG-SOFT Visual MIB Builder Version 4.0 Build 347
-- Monday, January 15, 2018 at 12:49:51
--

--  HUAWEI-SAN-MIB.mib
-- MIB generated by MG-SOFT Visual MIB Builder Version 4.0 Build 347
-- Tuesday, December 26, 2017 at 20:15:10
-- 
--  HUAWEI-DEVICE-MAN-MIB.mib
-- MIB generated by MG-SOFT Visual MIB Builder Version 4.0 Build 347
-- Tuesday, December 27, 2016 at 17:53:50
-- 

	HUAWEI-SAN-MIB DEFINITIONS ::= BEGIN
 
		IMPORTS
			OBJECT-GROUP, MODULE-COMPLIANCE			
				FROM SNMPv2-CONF			
			enterprises, Unsigned32, OBJECT-TYPE, MODULE-IDENTITY			
				FROM SNMPv2-SMI;
	
	
		storage MODULE-IDENTITY 
			LAST-UPDATED "201612171010Z"		-- December 17, 2016 at 10:10 GMT
			ORGANIZATION 
				"Huawei Technologies Co.,Ltd."
			CONTACT-INFO 
				"Huawei Industrial Base
				Bantian, Longgang
				Shenzhen 518129
				People's Republic of China
				Website: http://www.huawei.com
				Email: support@huawei.com"
			DESCRIPTION 
				"The HUAWEI-SAN-MIB contains objects to query the MappingViews information."
			::= { products 251 }

		
	
--
-- Node definitions
--
	
--  December 17, 2016 at 10:10 GMT
-- 
-- Node definitions
-- 
--  December 17, 2016 at 10:10 GMT
-- 
-- Node definitions
-- 
		huawei OBJECT IDENTIFIER ::= { enterprises 2011 }

		
		products OBJECT IDENTIFIER ::= { huawei 2 }

		
		san OBJECT IDENTIFIER ::= { storage 23 }

		-- 1.3.6.1.4.1.2011.2.251.23.245
		hwInfoMappingViewTable OBJECT-TYPE
			SYNTAX SEQUENCE OF HwInfoMappingViewEntry
			MAX-ACCESS not-accessible
			STATUS current
			DESCRIPTION
				"This table provides information about MappingViews."
			::= { san 245 }

		-- 1.3.6.1.4.1.2011.2.251.23.245.1
		hwInfoMappingViewEntry OBJECT-TYPE
			SYNTAX HwInfoMappingViewEntry
			MAX-ACCESS not-accessible
			STATUS current
			DESCRIPTION
				"A table containing the part component."
			INDEX { hwInfoMappingViewID }
			::= { hwInfoMappingViewTable 1 }

		
		HwInfoMappingViewEntry ::=
			SEQUENCE { 
				hwInfoMappingViewID
					OCTET STRING,
				hwInfoMappingViewName
					OCTET STRING,
				hwInfoMappingViewInbandCommand
					Unsigned32,
				hwInfoMappingViewLunGroupID
					OCTET STRING,
				hwInfoMappingViewLunGroupName
					OCTET STRING,
				hwInfoMappingViewHostGroupID
					OCTET STRING,
				hwInfoMappingViewHostGroupName
					OCTET STRING,
				hwInfoMappingViewPortGroupID
					OCTET STRING,
				hwInfoMappingViewPortGroupName
					OCTET STRING
			 }

		-- 1.3.6.1.4.1.2011.2.251.23.245.1.1
		hwInfoMappingViewID OBJECT-TYPE
			SYNTAX OCTET STRING
			MAX-ACCESS read-only
			STATUS current
			DESCRIPTION
				"ID of an Mapping View."
			::= { hwInfoMappingViewEntry 1 }

		-- 1.3.6.1.4.1.2011.2.251.23.245.1.2
		hwInfoMappingViewName OBJECT-TYPE
			SYNTAX OCTET STRING
			MAX-ACCESS read-only
			STATUS current
			DESCRIPTION
				"Name of Mapping View."
			::= { hwInfoMappingViewEntry 2 }

		-- 1.3.6.1.4.1.2011.2.251.23.245.1.3
		hwInfoMappingViewInbandCommand OBJECT-TYPE
			SYNTAX Unsigned32
			MAX-ACCESS read-only
			STATUS current
			DESCRIPTION
				"Whether to enable the	command device
				0: enable
				1: disable"
			::= { hwInfoMappingViewEntry 3 }

		-- 1.3.6.1.4.1.2011.2.251.23.245.1.4
		hwInfoMappingViewLunGroupID OBJECT-TYPE
			SYNTAX OCTET STRING
			MAX-ACCESS read-only
			STATUS current
			DESCRIPTION
				"ID of Lun Group in Mapping View."
			::= { hwInfoMappingViewEntry 4 }

		-- 1.3.6.1.4.1.2011.2.251.23.245.1.5
		hwInfoMappingViewLunGroupName OBJECT-TYPE
			SYNTAX OCTET STRING
			MAX-ACCESS read-only
			STATUS current
			DESCRIPTION
				"Name of Lun Group in Mapping View."
			::= { hwInfoMappingViewEntry 5 }

		-- 1.3.6.1.4.1.2011.2.251.23.245.1.6
		hwInfoMappingViewHostGroupID OBJECT-TYPE
			SYNTAX OCTET STRING
			MAX-ACCESS read-only
			STATUS current
			DESCRIPTION
				"ID of Host Group in Mapping View."
			::= { hwInfoMappingViewEntry 6 }

		-- 1.3.6.1.4.1.2011.2.251.23.245.1.7
		hwInfoMappingViewHostGroupName OBJECT-TYPE
			SYNTAX OCTET STRING
			MAX-ACCESS read-only
			STATUS current
			DESCRIPTION
				"Name of Lun Group in Mapping View."
			::= { hwInfoMappingViewEntry 7 }

		-- 1.3.6.1.4.1.2011.2.251.23.245.1.8
		hwInfoMappingViewPortGroupID OBJECT-TYPE
			SYNTAX OCTET STRING
			MAX-ACCESS read-only
			STATUS current
			DESCRIPTION
				"ID of Port Group in Mapping View."
			::= { hwInfoMappingViewEntry 8 }

		-- 1.3.6.1.4.1.2011.2.251.23.245.1.9
		hwInfoMappingViewPortGroupName OBJECT-TYPE
			SYNTAX OCTET STRING
			MAX-ACCESS read-only
			STATUS current
			DESCRIPTION
				"Name of Port Group in Mapping View."
			::= { hwInfoMappingViewEntry 9 }

		
		isoConformance OBJECT IDENTIFIER ::= { iso 6 }

		
		isoGroups OBJECT IDENTIFIER ::= { isoConformance 1 }

		
		currentObjectGroup OBJECT-GROUP
			OBJECTS { hwInfoMappingViewID, hwInfoMappingViewName, hwInfoMappingViewInbandCommand, hwInfoMappingViewLunGroupID, hwInfoMappingViewLunGroupName, 
				hwInfoMappingViewHostGroupID, hwInfoMappingViewHostGroupName, hwInfoMappingViewPortGroupID, hwInfoMappingViewPortGroupName }
			STATUS current
			DESCRIPTION 
				"Enter the description of the created OBJECT-GROUP."
			::= { isoGroups 1 }

		
		isoCompliances OBJECT IDENTIFIER ::= { isoConformance 2 }

		
--   this module
		basicCompliance MODULE-COMPLIANCE
			STATUS current
			DESCRIPTION 
				"Enter the description of the created MODULE-COMPLIANCE."
			MODULE HUAWEI-DEVICE-MAN-MIB
				MANDATORY-GROUPS { currentObjectGroup }
			::= { isoCompliances 1 }

		
	
	END

--
-- HUAWEI-SAN-MIB.mib
--
