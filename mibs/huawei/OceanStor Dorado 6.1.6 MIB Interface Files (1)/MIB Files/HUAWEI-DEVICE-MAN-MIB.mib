--
-- HUAWEI-DEVICE-MAN-MIB.mib
-- MIB generated by MG-SOFT Visual MIB Builder Version 4.0 Build 347
-- Tuesday, December 27, 2016 at 17:53:50
--

	HUAWEI-DEVICE-MAN-MIB DEFINITIONS ::= BEGIN
 
		IMPORTS
			OBJECT-GROUP, MODULE-COMPLIANCE			
				FROM SNMPv2-CONF			
			enterprises, Unsigned32, OBJECT-TYPE, MODULE-IDENTITY			
				FROM SNMPv2-SMI;
	
	
		storage MODULE-IDENTITY 
			LAST-UPDATED "201612171010Z"		-- December 17, 2016 at 10:10 GMT
			ORGANIZATION 
				"Huawei Technologies Co.,Ltd."
			CONTACT-INFO 
				"Huawei Industrial Base
				Bantian, Longgang
				Shenzhen 518129
				People's Republic of China
				Website: http://www.huawei.com
				Email: support@huawei.com"
			DESCRIPTION 
				"The HUAWEI-DEVICE-MAN-MIB contains objects to query the IB port information."
			::= { products 251 }

		
	
--
-- Node definitions
--
	
		huawei OBJECT IDENTIFIER ::= { enterprises 2011 }

		
		products OBJECT IDENTIFIER ::= { huawei 2 }

		
		deviceManager OBJECT IDENTIFIER ::= { storage 22 }

		-- 1.3.6.1.4.1.2011.2.251.22.16500
		hwInfoPortIBTable OBJECT-TYPE
			SYNTAX SEQUENCE OF HwInfoPortIBEntry
			MAX-ACCESS not-accessible
			STATUS current
			DESCRIPTION
				"This table is used to query information about InfiniBand ports."
			::= { deviceManager 16500 }

		-- 1.3.6.1.4.1.2011.2.251.22.16500.1
		hwInfoPortIBEntry OBJECT-TYPE
			SYNTAX HwInfoPortIBEntry
			MAX-ACCESS not-accessible
			STATUS current
			DESCRIPTION
				"A table containing the part component."
			INDEX { hwInfoPortIBID }
			::= { hwInfoPortIBTable 1 }

		
		HwInfoPortIBEntry ::=
			SEQUENCE { 
				hwInfoPortIBID
					OCTET STRING,
				hwInfoPortIBParentType
					Unsigned32,
				hwInfoPortIBParentID
					OCTET STRING,
				hwInfoPortIBLocation
					OCTET STRING,
				hwInfoPortIBHealthStatus
					Unsigned32,
				hwInfoPortIBRunningStatus
					Unsigned32,
				hwInfoPortIBType
					Unsigned32,
				hwInfoPortIBWorkingRate
					Unsigned32,
				hwInfoPortIBWWN
					OCTET STRING,
				hwInfoPortIBRole
					Unsigned32,
				hwInfoPortIBSymbolError
					Unsigned32,
				hwInfoPortIBLinkErrorRecovery
					Unsigned32,
				hwInfoPortIBReceiveErrors
					Unsigned32,
				hwInfoPortIBRemoteReceiveErrors
					Unsigned32,
				hwInfoPortIBReceiveTransmitErrors
					Unsigned32,
				hwInfoPortIBNotSendPacakges
					Unsigned32,
				hwInfoPortIBReceiveConstraintErrors
					Unsigned32,
				hwInfoPortIBLinkErrors
					Unsigned32,
				hwInfoPortIBBufferOverrunErrors
					Unsigned32,
				hwInfoPortIBStartTime
					OCTET STRING,
				hwInfoPortIBMaxSpeed
					Unsigned32
			 }

		-- 1.3.6.1.4.1.2011.2.251.22.16500.1.1
		hwInfoPortIBID OBJECT-TYPE
			SYNTAX OCTET STRING
			MAX-ACCESS read-only
			STATUS current
			DESCRIPTION
				"ID of an InfiniBand port, and it's the table index."
			::= { hwInfoPortIBEntry 1 }

		-- 1.3.6.1.4.1.2011.2.251.22.16500.1.2
		hwInfoPortIBParentType OBJECT-TYPE
			SYNTAX Unsigned32
			MAX-ACCESS read-only
			STATUS current
			DESCRIPTION
				"Parent type of an InfiniBand port. Possible values are:
				207: controller
				208: expansion board
				209: interface module"
			::= { hwInfoPortIBEntry 2 }

		-- 1.3.6.1.4.1.2011.2.251.22.16500.1.3
		hwInfoPortIBParentID OBJECT-TYPE
			SYNTAX OCTET STRING
			MAX-ACCESS read-only
			STATUS current
			DESCRIPTION
				"Parent ID of an InfiniBand port."
			::= { hwInfoPortIBEntry 3 }

		-- 1.3.6.1.4.1.2011.2.251.22.16500.1.4
		hwInfoPortIBLocation OBJECT-TYPE
			SYNTAX OCTET STRING
			MAX-ACCESS read-only
			STATUS current
			DESCRIPTION
				"Location of an InfiniBand port."
			::= { hwInfoPortIBEntry 4 }

		-- 1.3.6.1.4.1.2011.2.251.22.16500.1.5
		hwInfoPortIBHealthStatus OBJECT-TYPE
			SYNTAX Unsigned32
			MAX-ACCESS read-only
			STATUS current
			DESCRIPTION
				"Health status of an InfiniBand port. For details, see:
				1: Normal
				2: Fault
				3: Pre-Fail
				4: Partially Broken
				5: Degraded
				6: Bad Sectors Found
				7: Bit Errors Found
				8: Consistent
				9: Inconsistent
				10: Busy
				11: No Input
				12: Low Battery
				13: Single Link Fault
				14: Invalid
				15: Write Protect
				16: Single Link
				17: No Redundant Link
				18: Offine
				"
			::= { hwInfoPortIBEntry 5 }

		-- 1.3.6.1.4.1.2011.2.251.22.16500.1.6
		hwInfoPortIBRunningStatus OBJECT-TYPE
			SYNTAX Unsigned32
			MAX-ACCESS read-only
			STATUS current
			DESCRIPTION
				"Operating status of an InfiniBand port. For details, see:
				1: Normal
				2: Running
				3: Not running
				4: Not existed
				5: Sleep in high temperature
				6: Starting
				7: Power failure rotection
				8: Spin down
				9: Started
				10: Link Up
				11: Link Down
				12: Powering on
				13: Powered off
				14: Pre-copy
				15: Copyback
				16: Reconstruction
				17: Expansion
				18: Unformatted
				19: Formatting
				20: Unmapped
				21: Initial synchronizing
				22: Consistent
				23: Synchronizing
				24: Synchronized
				25: Unsynchronized
				26: Split
				27: Online
				28: Offline
				29: Locked
				30: Enabled
				31: Disabled
				32: Balancing
				33: To be recovered
				34: Interrupted
				35: Invalid
				36: Not start
				37: Queuing
				38: Stopped
				39: Copying
				40: Completed
				41: Paused
				42: Reverse synchronizing
				43: Activated
				44: Restore
				45: Inactive
				46: Idle
				47: Powering off
				48: Charging
				49: Charging completed
				50: Discharging
				51: Upgrading
				52: Power Lost
				53: Initializing
				54: Apply change
				55: Online disable
				56: Offline disable
				57: Online frozen
				58: Offline frozen
				59: Closed
				60: Removing
				61: In service
				62: Out of service
				63: Running normal
				64: Running fail
				65: Running success
				66: Running success
				67: Running failed
				68: Waiting
				69: Canceling
				70: Canceled
				71: About to synchronize
				72: Synchronizing data
				73: Failed to synchronize
				74: Fault
				75: Migrating
				76: Migrated
				77: Activating
				78: Deactivating
				79: Start failed
				80: Stop failed
				81: Decommissioning
				82: Decommissioned
				83: Recommissioning
				84: Replacing node
				85: Scheduling
				86: Pausing
				87: Suspending
				88: Suspended
				89: Overload
				90: To be switch
				91: Switching
				92: To be cleanup
				93: Forced start
				94: Error
				95: Job completed
				96: Partition Migrating
				97: Mount
				98: Umount
				99: INSTALLING
				100: To Be Synchronized
				101: Connecting
				102: Service Switching
				103: Power-on failed
				104: REPAIRING
				105: abnormal
				106: Deleting
				107: Modifying
				108: Running(clearing data)
				109: Running(synchronizing data)
				110: Standby
				111: STOPPING
				112: RESTORE FAULT
				113: Cut Over
				114: Erasing
				115: Verifying
				119: Creating
				"
			::= { hwInfoPortIBEntry 6 }

		-- 1.3.6.1.4.1.2011.2.251.22.16500.1.7
		hwInfoPortIBType OBJECT-TYPE
			SYNTAX Unsigned32
			MAX-ACCESS read-only
			STATUS current
			DESCRIPTION
				"Logical type of an InfiniBand port. For details, see:
				0: HOST
				1: EXP
				2: MNGT
				3: INNER
				4: MAINTENANCE
				5: MNGT_SRV
				6: MAINTENANCE_SRV
				7: BACKUP_MGR
				8: PRODUCT_STORAGE
				9: BACKUP_STORAGE
				10: ETH_NOT_CONFIG
				11: IP_SCALE_OUT
				"
			::= { hwInfoPortIBEntry 7 }

		-- 1.3.6.1.4.1.2011.2.251.22.16500.1.8
		hwInfoPortIBWorkingRate OBJECT-TYPE
			SYNTAX Unsigned32
			MAX-ACCESS read-only
			STATUS current
			DESCRIPTION
				"Working rate of an InfiniBand port (unit: Mbit/s). If the parameter value is 4294967295, this parameter is invalid."
			::= { hwInfoPortIBEntry 8 }

		-- 1.3.6.1.4.1.2011.2.251.22.16500.1.9
		hwInfoPortIBWWN OBJECT-TYPE
			SYNTAX OCTET STRING
			MAX-ACCESS read-only
			STATUS current
			DESCRIPTION
				"WWN of an InfiniBand port."
			::= { hwInfoPortIBEntry 9 }

		-- 1.3.6.1.4.1.2011.2.251.22.16500.1.10
		hwInfoPortIBRole OBJECT-TYPE
			SYNTAX Unsigned32
			MAX-ACCESS read-only
			STATUS current
			DESCRIPTION
				"Role of an InfiniBand port. Possible values are:
				2: initiator
				3: target
				4: initiator and target
				4294967295: invalid
				"
			::= { hwInfoPortIBEntry 10 }

		-- 1.3.6.1.4.1.2011.2.251.22.16500.1.11
		hwInfoPortIBSymbolError OBJECT-TYPE
			SYNTAX Unsigned32
			MAX-ACCESS read-only
			STATUS current
			DESCRIPTION
				"Symbol error statistics of an InfiniBand port."
			::= { hwInfoPortIBEntry 11 }

		-- 1.3.6.1.4.1.2011.2.251.22.16500.1.12
		hwInfoPortIBLinkErrorRecovery OBJECT-TYPE
			SYNTAX Unsigned32
			MAX-ACCESS read-only
			STATUS current
			DESCRIPTION
				"Statistics of rectifying an InfiniBand port's connection errors."
			::= { hwInfoPortIBEntry 12 }

		-- 1.3.6.1.4.1.2011.2.251.22.16500.1.13
		hwInfoPortIBReceiveErrors OBJECT-TYPE
			SYNTAX Unsigned32
			MAX-ACCESS read-only
			STATUS current
			DESCRIPTION
				"InfiniBand port receiving errors."
			::= { hwInfoPortIBEntry 13 }

		-- 1.3.6.1.4.1.2011.2.251.22.16500.1.14
		hwInfoPortIBRemoteReceiveErrors OBJECT-TYPE
			SYNTAX Unsigned32
			MAX-ACCESS read-only
			STATUS current
			DESCRIPTION
				"InfiniBand port remotely receiving errors."
			::= { hwInfoPortIBEntry 14 }

		-- 1.3.6.1.4.1.2011.2.251.22.16500.1.15
		hwInfoPortIBReceiveTransmitErrors OBJECT-TYPE
			SYNTAX Unsigned32
			MAX-ACCESS read-only
			STATUS current
			DESCRIPTION
				"InfiniBand port receiving and forwarding errors."
			::= { hwInfoPortIBEntry 15 }

		-- 1.3.6.1.4.1.2011.2.251.22.16500.1.16
		hwInfoPortIBNotSendPacakges OBJECT-TYPE
			SYNTAX Unsigned32
			MAX-ACCESS read-only
			STATUS current
			DESCRIPTION
				"Count of packets that are not sent by an InfiniBand port."
			::= { hwInfoPortIBEntry 16 }

		-- 1.3.6.1.4.1.2011.2.251.22.16500.1.17
		hwInfoPortIBReceiveConstraintErrors OBJECT-TYPE
			SYNTAX Unsigned32
			MAX-ACCESS read-only
			STATUS current
			DESCRIPTION
				"InfiniBand port receiving constraint errors."
			::= { hwInfoPortIBEntry 17 }

		-- 1.3.6.1.4.1.2011.2.251.22.16500.1.18
		hwInfoPortIBLinkErrors OBJECT-TYPE
			SYNTAX Unsigned32
			MAX-ACCESS read-only
			STATUS current
			DESCRIPTION
				"Connection error of an InfiniBand port."
			::= { hwInfoPortIBEntry 18 }

		-- 1.3.6.1.4.1.2011.2.251.22.16500.1.19
		hwInfoPortIBBufferOverrunErrors OBJECT-TYPE
			SYNTAX Unsigned32
			MAX-ACCESS read-only
			STATUS current
			DESCRIPTION
				"Buffer overflow error of an InfiniBand port."
			::= { hwInfoPortIBEntry 19 }

		-- 1.3.6.1.4.1.2011.2.251.22.16500.1.20
		hwInfoPortIBStartTime OBJECT-TYPE
			SYNTAX OCTET STRING
			MAX-ACCESS read-only
			STATUS current
			DESCRIPTION
				"Start time of an InfiniBand port."
			::= { hwInfoPortIBEntry 20 }

		-- 1.3.6.1.4.1.2011.2.251.22.16500.1.21
		hwInfoPortIBMaxSpeed OBJECT-TYPE
			SYNTAX Unsigned32
			MAX-ACCESS read-only
			STATUS current
			DESCRIPTION
				"Maximum rate of an InfiniBand port (unit: Mbit/s)."
			::= { hwInfoPortIBEntry 21 }

		
		isoConformance OBJECT IDENTIFIER ::= { iso 6 }

		
		isoGroups OBJECT IDENTIFIER ::= { isoConformance 1 }

		
		currentObjectGroup OBJECT-GROUP
			OBJECTS { hwInfoPortIBID, hwInfoPortIBParentType, hwInfoPortIBParentID, hwInfoPortIBLocation, hwInfoPortIBHealthStatus, 
				hwInfoPortIBRunningStatus, hwInfoPortIBType, hwInfoPortIBWorkingRate, hwInfoPortIBWWN, hwInfoPortIBRole, 
				hwInfoPortIBSymbolError, hwInfoPortIBLinkErrorRecovery, hwInfoPortIBReceiveErrors, hwInfoPortIBRemoteReceiveErrors, hwInfoPortIBReceiveTransmitErrors, 
				hwInfoPortIBNotSendPacakges, hwInfoPortIBReceiveConstraintErrors, hwInfoPortIBLinkErrors, hwInfoPortIBBufferOverrunErrors, hwInfoPortIBStartTime, 
				hwInfoPortIBMaxSpeed }
			STATUS current
			DESCRIPTION 
				"Enter the description of the created OBJECT-GROUP."
			::= { isoGroups 1 }

		
		isoCompliances OBJECT IDENTIFIER ::= { isoConformance 2 }

		
		basicCompliance MODULE-COMPLIANCE
			STATUS current
			DESCRIPTION 
				"Enter the description of the created MODULE-COMPLIANCE."
			MODULE -- this module
				MANDATORY-GROUPS { currentObjectGroup }
			::= { isoCompliances 1 }

		
	
	END

--
-- HUAWEI-DEVICE-MAN-MIB.mib
--
