--
-- HUAWEI-STORAGE-SPACE-MIB.mib
-- MIB generated by MG-SOFT Visual MIB Builder Version 4.0 Build 347
-- Monday, January 15, 2018 at 15:22:18
--

--  HUAWEI-STORAGE-SPACE-MIB.mib
-- MIB generated by MG-SOFT Visual MIB Builder Version 3.0 Build 253
-- Wednesday, May 25, 2016 at 11:41:14
-- 
--  HUAWEI-STORAGE-SPACE-MIB.mib
-- MIB generated by MG-SOFT Visual MIB Builder Version 3.0 Build 253
-- Tuesday, May 24, 2016 at 19:20:59
-- 
--  HUAWEI-STORAGE-SPACE-MIB.mib
-- MIB generated by MG-SOFT Visual MIB Builder Version 3.0 Build 253
-- Tuesday, April 05, 2016 at 11:03:12
-- 
--  HUAWEI-STORAGE-SPACE-MIB.mib
-- MIB generated by MG-SOFT Visual MIB Builder Version 3.0 Build 253
-- Friday, March 18, 2016 at 19:31:56
-- 
--  HUAWEI-STORAGE-SPACE-MIB.mib
-- MIB generated by MG-SOFT Visual MIB Builder Version 3.0 Build 253
-- Friday, March 11, 2016 at 15:20:03
-- 
--  HUAWEI-STORAGE-SPACE-MIB.mib
-- MIB generated by MG-SOFT Visual MIB Builder Version 3.0 Build 253
-- Tuesday, February 23, 2016 at 15:43:58
-- 
--  HUAWEI-STORAGE-SPACE-MIB.mib
-- MIB generated by MG-SOFT Visual MIB Builder Version 4.0 Build 347
-- Wednesday, October 15, 2014 at 11:21:02
-- 

	HUAWEI-STORAGE-SPACE-MIB DEFINITIONS ::= BEGIN
 
		IMPORTS
			OBJECT-GROUP, MODULE-COMPLIANCE			
				FROM SNMPv2-CONF			
			enterprises, Unsigned32, Counter64, OBJECT-TYPE, 
			MODULE-IDENTITY			
				FROM SNMPv2-SMI			
			TEXTUAL-CONVENTION			
				FROM SNMPv2-TC;
	
	
		hwStorage MODULE-IDENTITY 
			LAST-UPDATED "201603181930Z"		-- March 18, 2016 at 19:30 GMT
			ORGANIZATION 
				"Huawei Technologies Co.,Ltd."
			CONTACT-INFO 
				"Huawei Industrial Base
				Bantian, Longgang
				Shenzhen 518129
				People's Republic of China
				Website: http://www.huawei.com
				Email: support@huawei.com"
			DESCRIPTION 
				"The HUAWEI-STORAGE-SPACE-MIB contains objects to query the Storage Space module informations."
			REVISION "201304061354Z"		-- April 06, 2013 at 13:54 GMT
			DESCRIPTION 
				" "
			::= { huaweistorage 4 }

		
	
--
-- Textual conventions
--
	
--  March 18, 2016 at 19:30 GMT
-- April 06, 2013 at 13:54 GMT
-- 
-- Textual conventions
-- 
--  March 18, 2016 at 19:30 GMT
-- April 06, 2013 at 13:54 GMT
-- 
-- Textual conventions
-- 
--  March 18, 2016 at 19:30 GMT
-- April 06, 2013 at 13:54 GMT
-- 
-- Textual conventions
-- 
--  March 18, 2016 at 19:30 GMT
-- April 06, 2013 at 13:54 GMT
-- 
-- Textual conventions
-- 
--  August 11, 2010 at 12:39 GMT
-- April 06, 2013 at 13:54 GMT
-- 
-- Textual conventions
-- 
--  August 11, 2010 at 12:39 GMT
-- April 06, 2013 at 13:54 GMT
-- 
-- Textual conventions
-- 
--  August 11, 2010 at 12:39 GMT
-- April 06, 2013 at 13:54 GMT
-- 
-- Textual conventions
-- 
--  August 11, 2010 at 12:39 GMT
-- April 06, 2013 at 13:54 GMT
-- 
-- Textual conventions
-- 
		NodeCodeString ::= TEXTUAL-CONVENTION
			DISPLAY-HINT 
				"255a"
			STATUS current
			DESCRIPTION 
				"characters in length."
			SYNTAX OCTET STRING (SIZE (15..17))

	
--
-- Node definitions
--
	
--  Node definitions
-- 
-- Node definitions
-- 
		-- 1.3.6.1.4.1.34774
		huaweistorage OBJECT IDENTIFIER ::= { enterprises 34774 }

		
		-- 1.3.6.1.4.1.34774.4.1
		hwISM OBJECT IDENTIFIER ::= { hwStorage 1 }

		
		-- 1.3.6.1.4.1.34774.4.1.23
		hwStorageDevice OBJECT IDENTIFIER ::= { hwISM 23 }

		
		-- 1.3.6.1.4.1.34774.4.1.23.4
		hwSpaceInfo OBJECT IDENTIFIER ::= { hwStorageDevice 4 }

		
		-- 1.3.6.1.4.1.34774.4.1.23.4.1
		hwInfoDiskDomainTable OBJECT-TYPE
			SYNTAX SEQUENCE OF HwInfoDiskDomainEntry
			MAX-ACCESS not-accessible
			STATUS current
			DESCRIPTION
				"This table is used to check the disk domain information about a device."
			::= { hwSpaceInfo 1 }

		
		-- 1.3.6.1.4.1.34774.4.1.23.4.1.1
		hwInfoDiskDomainEntry OBJECT-TYPE
			SYNTAX HwInfoDiskDomainEntry
			MAX-ACCESS not-accessible
			STATUS current
			DESCRIPTION
				"A table containing the part component."
			INDEX { hwInfoDiskDomainID }
			::= { hwInfoDiskDomainTable 1 }

		
		HwInfoDiskDomainEntry ::=
			SEQUENCE { 
				hwInfoDiskDomainID
					OCTET STRING,
				hwInfoDiskDomainName
					OCTET STRING,
				hwInfoDiskDomainHealthStatus
					Unsigned32,
				hwInfoDiskDomainRunningStatus
					Unsigned32,
				hwInfoDiskDomainTotalCapacity
					Counter64,
				hwInfoDiskDomainFreeCapacity
					Counter64,
				hwInfoDiskDomainHotSpareCapacity
					Counter64,
				hwInfoDiskDomainUsedHotSpareCapacity
					Counter64
			 }

		-- 1.3.6.1.4.1.34774.4.1.23.4.1.1.1
		hwInfoDiskDomainID OBJECT-TYPE
			SYNTAX OCTET STRING
			MAX-ACCESS read-only
			STATUS current
			DESCRIPTION
				"Disk ID, table index."
			::= { hwInfoDiskDomainEntry 1 }

		
		-- 1.3.6.1.4.1.34774.4.1.23.4.1.1.2
		hwInfoDiskDomainName OBJECT-TYPE
			SYNTAX OCTET STRING
			MAX-ACCESS read-only
			STATUS current
			DESCRIPTION
				"Name of a disk domain."
			::= { hwInfoDiskDomainEntry 2 }

		
		-- 1.3.6.1.4.1.34774.4.1.23.4.1.1.3
		hwInfoDiskDomainHealthStatus OBJECT-TYPE
			SYNTAX Unsigned32
			MAX-ACCESS read-only
			STATUS current
			DESCRIPTION
				"Health status of a disk domain. For details, see:
				1 Normal
				2 Fault
				3 Pre-Fail
				4 Partially Broken
				5 Degraded
				6 Bad Sectors Found
				7 Bit Errors Found
				8 Consistent
				9 Inconsistent
				10 Busy
				11 No Input
				12 Low Battery
				13 Single Link Fault
				14 Invalid
				15 Write Protect
				16 single link
				17 No Redundant Link
				18 Offline"
			::= { hwInfoDiskDomainEntry 3 }

		
		-- 1.3.6.1.4.1.34774.4.1.23.4.1.1.4
		hwInfoDiskDomainRunningStatus OBJECT-TYPE
			SYNTAX Unsigned32
			MAX-ACCESS read-only
			STATUS current
			DESCRIPTION
				"Running status of a disk domain. For details, see:
				1: Normal
				2: Running
				3: Not running
				4: Not existed
				5: Sleep in high temperature
				6: Starting
				7: Power failure rotection
				8: Spin down
				9: Started
				10: Link Up
				11: Link Down
				12: Powering on
				13: Powered off
				14: Pre-copy
				15: Copyback
				16: Reconstruction
				17: Expansion
				18: Unformatted
				19: Formatting
				20: Unmapped
				21: Initial synchronizing
				22: Consistent
				23: Synchronizing
				24: Synchronized
				25: Unsynchronized
				26: Split
				27: Online
				28: Offline
				29: Locked
				30: Enabled
				31: Disabled
				32: Balancing
				33: To be recovered
				34: Interrupted
				35: Invalid
				36: Not start
				37: Queuing
				38: Stopped
				39: Copying
				40: Completed
				41: Paused
				42: Reverse synchronizing
				43: Activated
				44: Restore
				45: Inactive
				46: Idle
				47: Powering off
				48: Charging
				49: Charging completed
				50: Discharging
				51: Upgrading
				52: Power Lost
				53: Initializing
				54: Apply change
				55: Online disable
				56: Offline disable
				57: Online frozen
				58: Offline frozen
				59: Closed
				60: Removing
				61: In service
				62: Out of service
				63: Running normal
				64: Running fail
				65: Running success
				66: Running success
				67: Running failed
				68: Waiting
				69: Canceling
				70: Canceled
				71: About to synchronize
				72: Synchronizing data
				73: Failed to synchronize
				74: Fault
				75: Migrating
				76: Migrated
				77: Activating
				78: Deactivating
				79: Start failed
				80: Stop failed
				81: Decommissioning
				82: Decommissioned
				83: Recommissioning
				84: Replacing node
				85: Scheduling
				86: Pausing
				87: Suspending
				88: Suspended
				89: Overload
				90: To be switch
				91: Switching
				92: To be cleanup
				93: Forced start
				94: Error
				95: Job completed
				96: Partition Migrating
				97: Mount
				98: Umount
				99: INSTALLING
				100: To Be Synchronized
				101: Connecting
				102: Service Switching
				103: Power-on failed
				104: REPAIRING
				105: abnormal
				106: Deleting
				107: Modifying
				108: Running(clearing data)
				109: Running(synchronizing data)
				110: Standby
				111: STOPPING
				112: RESTORE FAULT
				113: Cut Over
				114: Erasing
				115: Verifying
				119: Creating"
			::= { hwInfoDiskDomainEntry 4 }

		
		-- 1.3.6.1.4.1.34774.4.1.23.4.1.1.5
		hwInfoDiskDomainTotalCapacity OBJECT-TYPE
			SYNTAX Counter64
			MAX-ACCESS read-only
			STATUS current
			DESCRIPTION
				"Total capacity of a disk domain. (unit: MB)."
			::= { hwInfoDiskDomainEntry 5 }

		
		-- 1.3.6.1.4.1.34774.4.1.23.4.1.1.6
		hwInfoDiskDomainFreeCapacity OBJECT-TYPE
			SYNTAX Counter64
			MAX-ACCESS read-only
			STATUS current
			DESCRIPTION
				"Free capacity of a disk domain. (unit: MB)."
			::= { hwInfoDiskDomainEntry 6 }

		
		-- 1.3.6.1.4.1.34774.4.1.23.4.1.1.7
		hwInfoDiskDomainHotSpareCapacity OBJECT-TYPE
			SYNTAX Counter64
			MAX-ACCESS read-only
			STATUS current
			DESCRIPTION
				"Hot spare capacity of a disk domain. (unit: MB)."
			::= { hwInfoDiskDomainEntry 7 }

		
		-- 1.3.6.1.4.1.34774.4.1.23.4.1.1.8
		hwInfoDiskDomainUsedHotSpareCapacity OBJECT-TYPE
			SYNTAX Counter64
			MAX-ACCESS read-only
			STATUS current
			DESCRIPTION
				"Used hot spare capacity of a disk domain. (unit: MB)."
			::= { hwInfoDiskDomainEntry 8 }

		
--       1.3.6.1.4.1.34774.4.1.23.4.2
-- 1.3.6.1.4.1.34774.4.1.23.4.2
-- 1.3.6.1.4.1.34774.4.1.23.4.2
-- 1.3.6.1.4.1.34774.4.1.23.4.2
-- 1.3.6.1.4.1.34774.4.1.23.4.2
-- 1.3.6.1.4.1.34774.4.1.23.4.2
		hwInfoStoragePoolTable OBJECT-TYPE
			SYNTAX SEQUENCE OF HwInfoStoragePoolEntry
			MAX-ACCESS not-accessible
			STATUS current
			DESCRIPTION
				"This table is used to check the storage pool information about a device."
			::= { hwSpaceInfo 2 }

		
		-- 1.3.6.1.4.1.34774.4.1.23.4.2.1
		hwInfoStoragePoolEntry OBJECT-TYPE
			SYNTAX HwInfoStoragePoolEntry
			MAX-ACCESS not-accessible
			STATUS current
			DESCRIPTION
				"A table containing the part component."
			INDEX { hwInfoStoragePoolID }
			::= { hwInfoStoragePoolTable 1 }

		
		HwInfoStoragePoolEntry ::=
			SEQUENCE { 
				hwInfoStoragePoolID
					OCTET STRING,
				hwInfoStoragePoolName
					OCTET STRING,
				hwInfoStoragePoolDiskDomainID
					OCTET STRING,
				hwInfoStoragePoolDiskDomainName
					OCTET STRING,
				hwInfoStoragePoolHealthStatus
					Unsigned32,
				hwInfoStoragePoolRunningStatus
					Unsigned32,
				hwInfoStoragePoolTotalCapacity
					Counter64,
				hwInfoStoragePoolSubscribedCapacity
					Counter64,
				hwInfoStoragePoolFreeCapacity
					Counter64,
				hwInfoStoragePoolProtectionCapacity
					Counter64,
				hwInfoStoragePoolFullThreshold
					Unsigned32,
				hwInfoStoragePoolLunTotalCapacity
					Counter64,
				hwInfoStoragePoolDataReductionRatio
					OCTET STRING,
				hwInfoStoragePoolDeduplicationRatio
					OCTET STRING,
				hwInfoStoragePoolCompressionRatio
					OCTET STRING
			 }

		-- 1.3.6.1.4.1.34774.4.1.23.4.2.1.1
		hwInfoStoragePoolID OBJECT-TYPE
			SYNTAX OCTET STRING
			MAX-ACCESS read-only
			STATUS current
			DESCRIPTION
				"ID of a storage pool, table index."
			::= { hwInfoStoragePoolEntry 1 }

		
		-- 1.3.6.1.4.1.34774.4.1.23.4.2.1.2
		hwInfoStoragePoolName OBJECT-TYPE
			SYNTAX OCTET STRING
			MAX-ACCESS read-only
			STATUS current
			DESCRIPTION
				"Name of a storage pool."
			::= { hwInfoStoragePoolEntry 2 }

		
		-- 1.3.6.1.4.1.34774.4.1.23.4.2.1.3
		hwInfoStoragePoolDiskDomainID OBJECT-TYPE
			SYNTAX OCTET STRING
			MAX-ACCESS read-only
			STATUS current
			DESCRIPTION
				"ID of the disk domain where a storage pool resides."
			::= { hwInfoStoragePoolEntry 3 }

		
		-- 1.3.6.1.4.1.34774.4.1.23.4.2.1.4
		hwInfoStoragePoolDiskDomainName OBJECT-TYPE
			SYNTAX OCTET STRING
			MAX-ACCESS read-only
			STATUS current
			DESCRIPTION
				"Name of the disk domain where a storage pool resides."
			::= { hwInfoStoragePoolEntry 4 }

		
		-- 1.3.6.1.4.1.34774.4.1.23.4.2.1.5
		hwInfoStoragePoolHealthStatus OBJECT-TYPE
			SYNTAX Unsigned32
			MAX-ACCESS read-only
			STATUS current
			DESCRIPTION
				"Health status of a storage pool. For details, see:
				1 Normal
				2 Fault
				3 Pre-Fail
				4 Partially Broken
				5 Degraded
				6 Bad Sectors Found
				7 Bit Errors Found
				8 Consistent
				9 Inconsistent
				10 Busy
				11 No Input
				12 Low Battery
				13 Single Link Fault
				14 Invalid
				15 Write Protect
				16 single link
				17 No Redundant Link
				18 Offline"
			::= { hwInfoStoragePoolEntry 5 }

		
		-- 1.3.6.1.4.1.34774.4.1.23.4.2.1.6
		hwInfoStoragePoolRunningStatus OBJECT-TYPE
			SYNTAX Unsigned32
			MAX-ACCESS read-only
			STATUS current
			DESCRIPTION
				"Operating status of a storage pool. For details, see:
				1: Normal
				2: Running
				3: Not running
				4: Not existed
				5: Sleep in high temperature
				6: Starting
				7: Power failure rotection
				8: Spin down
				9: Started
				10: Link Up
				11: Link Down
				12: Powering on
				13: Powered off
				14: Pre-copy
				15: Copyback
				16: Reconstruction
				17: Expansion
				18: Unformatted
				19: Formatting
				20: Unmapped
				21: Initial synchronizing
				22: Consistent
				23: Synchronizing
				24: Synchronized
				25: Unsynchronized
				26: Split
				27: Online
				28: Offline
				29: Locked
				30: Enabled
				31: Disabled
				32: Balancing
				33: To be recovered
				34: Interrupted
				35: Invalid
				36: Not start
				37: Queuing
				38: Stopped
				39: Copying
				40: Completed
				41: Paused
				42: Reverse synchronizing
				43: Activated
				44: Restore
				45: Inactive
				46: Idle
				47: Powering off
				48: Charging
				49: Charging completed
				50: Discharging
				51: Upgrading
				52: Power Lost
				53: Initializing
				54: Apply change
				55: Online disable
				56: Offline disable
				57: Online frozen
				58: Offline frozen
				59: Closed
				60: Removing
				61: In service
				62: Out of service
				63: Running normal
				64: Running fail
				65: Running success
				66: Running success
				67: Running failed
				68: Waiting
				69: Canceling
				70: Canceled
				71: About to synchronize
				72: Synchronizing data
				73: Failed to synchronize
				74: Fault
				75: Migrating
				76: Migrated
				77: Activating
				78: Deactivating
				79: Start failed
				80: Stop failed
				81: Decommissioning
				82: Decommissioned
				83: Recommissioning
				84: Replacing node
				85: Scheduling
				86: Pausing
				87: Suspending
				88: Suspended
				89: Overload
				90: To be switch
				91: Switching
				92: To be cleanup
				93: Forced start
				94: Error
				95: Job completed
				96: Partition Migrating
				97: Mount
				98: Umount
				99: INSTALLING
				100: To Be Synchronized
				101: Connecting
				102: Service Switching
				103: Power-on failed
				104: REPAIRING
				105: abnormal
				106: Deleting
				107: Modifying
				108: Running(clearing data)
				109: Running(synchronizing data)
				110: Standby
				111: STOPPING
				112: RESTORE FAULT
				113: Cut Over
				114: Erasing
				115: Verifying
				119: Creating"
			::= { hwInfoStoragePoolEntry 6 }

		
		-- 1.3.6.1.4.1.34774.4.1.23.4.2.1.7
		hwInfoStoragePoolTotalCapacity OBJECT-TYPE
			SYNTAX Counter64
			MAX-ACCESS read-only
			STATUS current
			DESCRIPTION
				"Total capacity of a storage pool (unit: MB)."
			::= { hwInfoStoragePoolEntry 7 }

		
		-- 1.3.6.1.4.1.34774.4.1.23.4.2.1.8
		hwInfoStoragePoolSubscribedCapacity OBJECT-TYPE
			SYNTAX Counter64
			MAX-ACCESS read-only
			STATUS current
			DESCRIPTION
				"Used capacity of a storage pool (unit: MB)."
			::= { hwInfoStoragePoolEntry 8 }

		
		-- 1.3.6.1.4.1.34774.4.1.23.4.2.1.9
		hwInfoStoragePoolFreeCapacity OBJECT-TYPE
			SYNTAX Counter64
			MAX-ACCESS read-only
			STATUS current
			DESCRIPTION
				"Available capacity of a storage pool (unit: MB)."
			::= { hwInfoStoragePoolEntry 9 }

		
		-- 1.3.6.1.4.1.34774.4.1.23.4.2.1.10
		hwInfoStoragePoolProtectionCapacity OBJECT-TYPE
			SYNTAX Counter64
			MAX-ACCESS read-only
			STATUS current
			DESCRIPTION
				"Data protection capacity of a storage pool (unit: MB)."
			::= { hwInfoStoragePoolEntry 10 }

		
--       1.3.6.1.4.1.34774.4.1.23.4.2.1.14
-- 1.3.6.1.4.1.34774.4.1.23.4.2.1.14
-- 1.3.6.1.4.1.34774.4.1.23.4.2.1.14
-- 1.3.6.1.4.1.34774.4.1.23.4.2.1.14
-- 1.3.6.1.4.1.34774.4.1.23.4.2.1.14
-- 1.3.6.1.4.1.34774.4.1.23.4.2.1.14
		hwInfoStoragePoolFullThreshold OBJECT-TYPE
			SYNTAX Unsigned32
			MAX-ACCESS read-only
			STATUS current
			DESCRIPTION
				"Threshold of used capacity of a storage pool (unit: %)."
			::= { hwInfoStoragePoolEntry 14 }

		
--       1.3.6.1.4.1.34774.4.1.23.4.2.1.7
-- 1.3.6.1.4.1.34774.4.1.23.4.2.1.7
-- 1.3.6.1.4.1.34774.4.1.23.4.2.1.7
-- 1.3.6.1.4.1.34774.4.1.23.4.2.1.7
-- 1.3.6.1.4.1.34774.4.1.23.4.2.1.7
-- 1.3.6.1.4.1.34774.4.1.23.4.2.1.7
		-- 1.3.6.1.4.1.34774.4.1.23.4.2.1.23
		hwInfoStoragePoolLunTotalCapacity OBJECT-TYPE
			SYNTAX Counter64
			MAX-ACCESS read-only
			STATUS current
			DESCRIPTION
				"Lun capacity of a storage pool (unit: MB)."
			::= { hwInfoStoragePoolEntry 23 }

		
		-- 1.3.6.1.4.1.34774.4.1.23.4.2.1.24
		hwInfoStoragePoolDataReductionRatio OBJECT-TYPE
			SYNTAX OCTET STRING
			MAX-ACCESS read-only
			STATUS current
			DESCRIPTION
				"Data Reduction Ratio."
			::= { hwInfoStoragePoolEntry 24 }

		
		-- 1.3.6.1.4.1.34774.4.1.23.4.2.1.25
		hwInfoStoragePoolDeduplicationRatio OBJECT-TYPE
			SYNTAX OCTET STRING
			MAX-ACCESS read-only
			STATUS current
			DESCRIPTION
				"Data Deduplication Ratio."
			::= { hwInfoStoragePoolEntry 25 }

		
		-- 1.3.6.1.4.1.34774.4.1.23.4.2.1.26
		hwInfoStoragePoolCompressionRatio OBJECT-TYPE
			SYNTAX OCTET STRING
			MAX-ACCESS read-only
			STATUS current
			DESCRIPTION
				"Data Compression Ratio."
			::= { hwInfoStoragePoolEntry 26 }

		
--       1.3.6.1.4.1.34774.4.1.23.4.4
-- 1.3.6.1.4.1.34774.4.1.23.4.4
-- 1.3.6.1.4.1.34774.4.1.23.4.4
-- 1.3.6.1.4.1.34774.4.1.23.4.4
-- 1.3.6.1.4.1.34774.4.1.23.4.4
		-- 1.3.6.1.4.1.34774.4.1.23.4.4
		hwInfoPortGroupTable OBJECT-TYPE
			SYNTAX SEQUENCE OF HwInfoPortGroupEntry
			MAX-ACCESS not-accessible
			STATUS current
			DESCRIPTION
				"This table is used to check the port group information about a device."
			::= { hwSpaceInfo 4 }

		
		-- 1.3.6.1.4.1.34774.4.1.23.4.4.1
		hwInfoPortGroupEntry OBJECT-TYPE
			SYNTAX HwInfoPortGroupEntry
			MAX-ACCESS not-accessible
			STATUS current
			DESCRIPTION
				"A table containing the part component."
			INDEX { hwInfoPortGroupID }
			::= { hwInfoPortGroupTable 1 }

		
		HwInfoPortGroupEntry ::=
			SEQUENCE { 
				hwInfoPortGroupID
					OCTET STRING,
				hwInfoPortGroupName
					OCTET STRING,
				hwInfoPortGroupPortList
					OCTET STRING
			 }

		-- 1.3.6.1.4.1.34774.4.1.23.4.4.1.1
		hwInfoPortGroupID OBJECT-TYPE
			SYNTAX OCTET STRING
			MAX-ACCESS read-only
			STATUS current
			DESCRIPTION
				"ID of a port group, table index."
			::= { hwInfoPortGroupEntry 1 }

		
		-- 1.3.6.1.4.1.34774.4.1.23.4.4.1.2
		hwInfoPortGroupName OBJECT-TYPE
			SYNTAX OCTET STRING
			MAX-ACCESS read-only
			STATUS current
			DESCRIPTION
				"Name of a port group."
			::= { hwInfoPortGroupEntry 2 }

		
		-- 1.3.6.1.4.1.34774.4.1.23.4.4.1.3
		hwInfoPortGroupPortList OBJECT-TYPE
			SYNTAX OCTET STRING
			MAX-ACCESS read-only
			STATUS current
			DESCRIPTION
				"List of ports in a port group. 
				The format of list is: ID1: Type1: Location1, ID2: Type2: Location2…. The value of Type is:
				213: Port ETH
				212: Port FC
				252: Port FCoE"
			::= { hwInfoPortGroupEntry 3 }

		
		-- 1.3.6.1.4.1.34774.4.1.23.4.5
		hwInfoHostTable OBJECT-TYPE
			SYNTAX SEQUENCE OF HwInfoHostEntry
			MAX-ACCESS not-accessible
			STATUS current
			DESCRIPTION
				"This table is used to check the host information about a device."
			::= { hwSpaceInfo 5 }

		
		-- 1.3.6.1.4.1.34774.4.1.23.4.5.1
		hwInfoHostEntry OBJECT-TYPE
			SYNTAX HwInfoHostEntry
			MAX-ACCESS not-accessible
			STATUS current
			DESCRIPTION
				"A table containing the part component."
			INDEX { hwInfoHostID }
			::= { hwInfoHostTable 1 }

		
		HwInfoHostEntry ::=
			SEQUENCE { 
				hwInfoHostID
					OCTET STRING,
				hwInfoHostName
					OCTET STRING,
				hwInfoHostLocation
					OCTET STRING,
				hwInfoHostHealthStatus
					Unsigned32,
				hwInfoHostRunningStatus
					Unsigned32,
				hwInfoHostOperatingSystem
					Unsigned32,
				hwInfoHostIPAddress
					OCTET STRING,
				hwInfoHostNetworkName
					OCTET STRING,
				hwInfoHostModel
					OCTET STRING
			 }

		-- 1.3.6.1.4.1.34774.4.1.23.4.5.1.1
		hwInfoHostID OBJECT-TYPE
			SYNTAX OCTET STRING
			MAX-ACCESS read-only
			STATUS current
			DESCRIPTION
				"Host ID, table index."
			::= { hwInfoHostEntry 1 }

		
		-- 1.3.6.1.4.1.34774.4.1.23.4.5.1.2
		hwInfoHostName OBJECT-TYPE
			SYNTAX OCTET STRING
			MAX-ACCESS read-only
			STATUS current
			DESCRIPTION
				"Host name."
			::= { hwInfoHostEntry 2 }

		
		-- 1.3.6.1.4.1.34774.4.1.23.4.5.1.3
		hwInfoHostLocation OBJECT-TYPE
			SYNTAX OCTET STRING
			MAX-ACCESS read-only
			STATUS current
			DESCRIPTION
				"Host location."
			::= { hwInfoHostEntry 3 }

		
		-- 1.3.6.1.4.1.34774.4.1.23.4.5.1.4
		hwInfoHostHealthStatus OBJECT-TYPE
			SYNTAX Unsigned32
			MAX-ACCESS read-only
			STATUS current
			DESCRIPTION
				"Host health status. For details, see:
				1 Normal
				2 Fault
				3 Pre-Fail
				4 Partially Broken
				5 Degraded
				6 Bad Sectors Found
				7 Bit Errors Found
				8 Consistent
				9 Inconsistent
				10 Busy
				11 No Input
				12 Low Battery
				13 Single Link Fault
				14 Invalid
				15 Write Protect
				16 single link
				17 No Redundant Link
				18 Offline"
			::= { hwInfoHostEntry 4 }

		
		-- 1.3.6.1.4.1.34774.4.1.23.4.5.1.5
		hwInfoHostRunningStatus OBJECT-TYPE
			SYNTAX Unsigned32
			MAX-ACCESS read-only
			STATUS current
			DESCRIPTION
				"Host operating status. For details, see:
				1: Normal
				2: Running
				3: Not running
				4: Not existed
				5: Sleep in high temperature
				6: Starting
				7: Power failure rotection
				8: Spin down
				9: Started
				10: Link Up
				11: Link Down
				12: Powering on
				13: Powered off
				14: Pre-copy
				15: Copyback
				16: Reconstruction
				17: Expansion
				18: Unformatted
				19: Formatting
				20: Unmapped
				21: Initial synchronizing
				22: Consistent
				23: Synchronizing
				24: Synchronized
				25: Unsynchronized
				26: Split
				27: Online
				28: Offline
				29: Locked
				30: Enabled
				31: Disabled
				32: Balancing
				33: To be recovered
				34: Interrupted
				35: Invalid
				36: Not start
				37: Queuing
				38: Stopped
				39: Copying
				40: Completed
				41: Paused
				42: Reverse synchronizing
				43: Activated
				44: Restore
				45: Inactive
				46: Idle
				47: Powering off
				48: Charging
				49: Charging completed
				50: Discharging
				51: Upgrading
				52: Power Lost
				53: Initializing
				54: Apply change
				55: Online disable
				56: Offline disable
				57: Online frozen
				58: Offline frozen
				59: Closed
				60: Removing
				61: In service
				62: Out of service
				63: Running normal
				64: Running fail
				65: Running success
				66: Running success
				67: Running failed
				68: Waiting
				69: Canceling
				70: Canceled
				71: About to synchronize
				72: Synchronizing data
				73: Failed to synchronize
				74: Fault
				75: Migrating
				76: Migrated
				77: Activating
				78: Deactivating
				79: Start failed
				80: Stop failed
				81: Decommissioning
				82: Decommissioned
				83: Recommissioning
				84: Replacing node
				85: Scheduling
				86: Pausing
				87: Suspending
				88: Suspended
				89: Overload
				90: To be switch
				91: Switching
				92: To be cleanup
				93: Forced start
				94: Error
				95: Job completed
				96: Partition Migrating
				97: Mount
				98: Umount
				99: INSTALLING
				100: To Be Synchronized
				101: Connecting
				102: Service Switching
				103: Power-on failed
				104: REPAIRING
				105: abnormal
				106: Deleting
				107: Modifying
				108: Running(clearing data)
				109: Running(synchronizing data)
				110: Standby
				111: STOPPING
				112: RESTORE FAULT
				113: Cut Over
				114: Erasing
				115: Verifying
				119: Creating"
			::= { hwInfoHostEntry 5 }

		
		-- 1.3.6.1.4.1.34774.4.1.23.4.5.1.6
		hwInfoHostOperatingSystem OBJECT-TYPE
			SYNTAX Unsigned32
			MAX-ACCESS read-only
			STATUS current
			DESCRIPTION
				"Host operating system. Possible values are:
				0: Linux
				1: Windows
				2: Solaris
				3: HP-UX
				4: AIX
				5: XenServer
				6: Mac OS
				7: VMware ESX
				8: VIS6000
				9: Windows Server 2012
				10: Oracle_VM
				11: OpenVMS
				12: Oracle_VM_Server_for_x86
				13: Oracle_VM_Server_for_SPARC"
			::= { hwInfoHostEntry 6 }

		
		-- 1.3.6.1.4.1.34774.4.1.23.4.5.1.7
		hwInfoHostIPAddress OBJECT-TYPE
			SYNTAX OCTET STRING
			MAX-ACCESS read-only
			STATUS current
			DESCRIPTION
				"Host IP address."
			::= { hwInfoHostEntry 7 }

		
		-- 1.3.6.1.4.1.34774.4.1.23.4.5.1.8
		hwInfoHostNetworkName OBJECT-TYPE
			SYNTAX OCTET STRING
			MAX-ACCESS read-only
			STATUS current
			DESCRIPTION
				"Host domain name."
			::= { hwInfoHostEntry 8 }

		
		-- 1.3.6.1.4.1.34774.4.1.23.4.5.1.9
		hwInfoHostModel OBJECT-TYPE
			SYNTAX OCTET STRING
			MAX-ACCESS read-only
			STATUS current
			DESCRIPTION
				"Host model."
			::= { hwInfoHostEntry 9 }

		
		-- 1.3.6.1.4.1.34774.4.1.23.4.6
		hwInfoHostGroupTable OBJECT-TYPE
			SYNTAX SEQUENCE OF HwInfoHostGroupEntry
			MAX-ACCESS not-accessible
			STATUS current
			DESCRIPTION
				"This table is used to check the host group information about a device."
			::= { hwSpaceInfo 6 }

		
		-- 1.3.6.1.4.1.34774.4.1.23.4.6.1
		hwInfoHostGroupEntry OBJECT-TYPE
			SYNTAX HwInfoHostGroupEntry
			MAX-ACCESS not-accessible
			STATUS current
			DESCRIPTION
				"A table containing the part component."
			INDEX { hwInfoHostGroupID }
			::= { hwInfoHostGroupTable 1 }

		
		HwInfoHostGroupEntry ::=
			SEQUENCE { 
				hwInfoHostGroupID
					OCTET STRING,
				hwInfoHostGroupName
					OCTET STRING,
				hwInfoHostGroupHostList
					OCTET STRING
			 }

		-- 1.3.6.1.4.1.34774.4.1.23.4.6.1.1
		hwInfoHostGroupID OBJECT-TYPE
			SYNTAX OCTET STRING
			MAX-ACCESS read-only
			STATUS current
			DESCRIPTION
				"ID of a host group, table index."
			::= { hwInfoHostGroupEntry 1 }

		
		-- 1.3.6.1.4.1.34774.4.1.23.4.6.1.2
		hwInfoHostGroupName OBJECT-TYPE
			SYNTAX OCTET STRING
			MAX-ACCESS read-only
			STATUS current
			DESCRIPTION
				"Name of a host group."
			::= { hwInfoHostGroupEntry 2 }

		
		-- 1.3.6.1.4.1.34774.4.1.23.4.6.1.3
		hwInfoHostGroupHostList OBJECT-TYPE
			SYNTAX OCTET STRING
			MAX-ACCESS read-only
			STATUS current
			DESCRIPTION
				"List of hosts in a host group. 
				The format of list is: ID1: Name1, ID2: Name2…"
			::= { hwInfoHostGroupEntry 3 }

		
		-- 1.3.6.1.4.1.34774.4.1.23.4.7
		hwInfoLunGroupTable OBJECT-TYPE
			SYNTAX SEQUENCE OF HwInfoLunGroupEntry
			MAX-ACCESS not-accessible
			STATUS current
			DESCRIPTION
				"This table is used to check the LUN group information about a device."
			::= { hwSpaceInfo 7 }

		
		-- 1.3.6.1.4.1.34774.4.1.23.4.7.1
		hwInfoLunGroupEntry OBJECT-TYPE
			SYNTAX HwInfoLunGroupEntry
			MAX-ACCESS not-accessible
			STATUS current
			DESCRIPTION
				"A table containing the part component."
			INDEX { hwInfoLunGroupID }
			::= { hwInfoLunGroupTable 1 }

		
		HwInfoLunGroupEntry ::=
			SEQUENCE { 
				hwInfoLunGroupID
					OCTET STRING,
				hwInfoLunGroupName
					OCTET STRING,
				hwInfoLunGroupLunList
					OCTET STRING
			 }

		-- 1.3.6.1.4.1.34774.4.1.23.4.7.1.1
		hwInfoLunGroupID OBJECT-TYPE
			SYNTAX OCTET STRING
			MAX-ACCESS read-only
			STATUS current
			DESCRIPTION
				"ID of a LUN group, table index."
			::= { hwInfoLunGroupEntry 1 }

		
		-- 1.3.6.1.4.1.34774.4.1.23.4.7.1.2
		hwInfoLunGroupName OBJECT-TYPE
			SYNTAX OCTET STRING
			MAX-ACCESS read-only
			STATUS current
			DESCRIPTION
				"Name of a LUN group."
			::= { hwInfoLunGroupEntry 2 }

		
		-- 1.3.6.1.4.1.34774.4.1.23.4.7.1.3
		hwInfoLunGroupLunList OBJECT-TYPE
			SYNTAX OCTET STRING
			MAX-ACCESS read-only
			STATUS current
			DESCRIPTION
				"List of LUNs in a LUN group. 
				The format of list is: ID1: Name1, ID2: Name2…"
			::= { hwInfoLunGroupEntry 3 }

		
		-- 1.3.6.1.4.1.34774.4.1.23.4.8
		hwInfoLunTable OBJECT-TYPE
			SYNTAX SEQUENCE OF HwInfoLunEntry
			MAX-ACCESS not-accessible
			STATUS current
			DESCRIPTION
				"This table is used to check the LUN information about a device."
			::= { hwSpaceInfo 8 }

		
		-- 1.3.6.1.4.1.34774.4.1.23.4.8.1
		hwInfoLunEntry OBJECT-TYPE
			SYNTAX HwInfoLunEntry
			MAX-ACCESS not-accessible
			STATUS current
			DESCRIPTION
				"A table containing the part component."
			INDEX { hwInfoLunID }
			::= { hwInfoLunTable 1 }

		
		HwInfoLunEntry ::=
			SEQUENCE { 
				hwInfoLunID
					OCTET STRING,
				hwInfoLunName
					OCTET STRING,
				hwInfoLunPoolID
					OCTET STRING,
				hwInfoLunPoolName
					OCTET STRING,
				hwInfoLunCapacity
					Counter64,
				hwInfoLunSubscribedCapacity
					Counter64,
				hwInfoLunProtectionCapacity
					Counter64,
				hwInfoLunSectorSize
					Unsigned32,
				hwInfoLunHealthStatus
					Unsigned32,
				hwInfoLunRunningStatus
					Unsigned32,
				hwInfoLunType
					Unsigned32,
				hwInfoLunIOPriority
					Unsigned32,
				hwInfoLunWWN
					OCTET STRING,
				hwInfoLunExposedToInitiator
					Unsigned32,
				hwInfoLunWritePolicy
					Unsigned32,
				hwInfoLunRunningWritePolicy
					Unsigned32,
				hwInfoLunPrefetchPolicy
					Unsigned32,
				hwInfoLunPrefetchValue
					Unsigned32,
				hwInfoLunOwnerController
					OCTET STRING,
				hwInfoLunWorkController
					OCTET STRING,
				hwInfoLunIsAddToLunGroup
					Unsigned32,
				hwInfoLunDIFSwitch
					Unsigned32,
				hwInfoLunRemoteLUNWWN
					OCTET STRING,
				hwInfoLunUsageType
					Unsigned32
			 }

		-- 1.3.6.1.4.1.34774.4.1.23.4.8.1.1
		hwInfoLunID OBJECT-TYPE
			SYNTAX OCTET STRING
			MAX-ACCESS read-only
			STATUS current
			DESCRIPTION
				"LUN ID"
			::= { hwInfoLunEntry 1 }

		
		-- 1.3.6.1.4.1.34774.4.1.23.4.8.1.2
		hwInfoLunName OBJECT-TYPE
			SYNTAX OCTET STRING
			MAX-ACCESS read-only
			STATUS current
			DESCRIPTION
				"LUN name"
			::= { hwInfoLunEntry 2 }

		
		-- 1.3.6.1.4.1.34774.4.1.23.4.8.1.3
		hwInfoLunPoolID OBJECT-TYPE
			SYNTAX OCTET STRING
			MAX-ACCESS read-only
			STATUS current
			DESCRIPTION
				"ID of the storage pool to which the LUN belongs."
			::= { hwInfoLunEntry 3 }

		
		-- 1.3.6.1.4.1.34774.4.1.23.4.8.1.4
		hwInfoLunPoolName OBJECT-TYPE
			SYNTAX OCTET STRING
			MAX-ACCESS read-only
			STATUS current
			DESCRIPTION
				"Name of the storage pool to which the LUN belongs."
			::= { hwInfoLunEntry 4 }

		
		-- 1.3.6.1.4.1.34774.4.1.23.4.8.1.5
		hwInfoLunCapacity OBJECT-TYPE
			SYNTAX Counter64
			MAX-ACCESS read-only
			STATUS current
			DESCRIPTION
				"Total capacity of the LUN (unit: MB)."
			::= { hwInfoLunEntry 5 }

		
		-- 1.3.6.1.4.1.34774.4.1.23.4.8.1.6
		hwInfoLunSubscribedCapacity OBJECT-TYPE
			SYNTAX Counter64
			MAX-ACCESS read-only
			STATUS current
			DESCRIPTION
				"Capacity usage quota of the LUN (unit: MB)."
			::= { hwInfoLunEntry 6 }

		
		-- 1.3.6.1.4.1.34774.4.1.23.4.8.1.7
		hwInfoLunProtectionCapacity OBJECT-TYPE
			SYNTAX Counter64
			MAX-ACCESS read-only
			STATUS current
			DESCRIPTION
				"Data protection capacity quota of the LUN (unit: KB)."
			::= { hwInfoLunEntry 7 }

		
		-- 1.3.6.1.4.1.34774.4.1.23.4.8.1.8
		hwInfoLunSectorSize OBJECT-TYPE
			SYNTAX Unsigned32
			MAX-ACCESS read-only
			STATUS current
			DESCRIPTION
				"Sector size of the LUN (unit: B)."
			::= { hwInfoLunEntry 8 }

		
		-- 1.3.6.1.4.1.34774.4.1.23.4.8.1.9
		hwInfoLunHealthStatus OBJECT-TYPE
			SYNTAX Unsigned32
			MAX-ACCESS read-only
			STATUS current
			DESCRIPTION
				"Health status of the LUN. For details, see:
				1 Normal
				2 Fault
				3 Pre-Fail
				4 Partially Broken
				5 Degraded
				6 Bad Sectors Found
				7 Bit Errors Found
				8 Consistent
				9 Inconsistent
				10 Busy
				11 No Input
				12 Low Battery
				13 Single Link Fault
				14 Invalid
				15 Write Protect
				16 single link
				17 No Redundant Link
				18 Offline"
			::= { hwInfoLunEntry 9 }

		
		-- 1.3.6.1.4.1.34774.4.1.23.4.8.1.10
		hwInfoLunRunningStatus OBJECT-TYPE
			SYNTAX Unsigned32
			MAX-ACCESS read-only
			STATUS current
			DESCRIPTION
				"Operating status of the LUN. For details, see:
				1: Normal
				2: Running
				3: Not running
				4: Not existed
				5: Sleep in high temperature
				6: Starting
				7: Power failure rotection
				8: Spin down
				9: Started
				10: Link Up
				11: Link Down
				12: Powering on
				13: Powered off
				14: Pre-copy
				15: Copyback
				16: Reconstruction
				17: Expansion
				18: Unformatted
				19: Formatting
				20: Unmapped
				21: Initial synchronizing
				22: Consistent
				23: Synchronizing
				24: Synchronized
				25: Unsynchronized
				26: Split
				27: Online
				28: Offline
				29: Locked
				30: Enabled
				31: Disabled
				32: Balancing
				33: To be recovered
				34: Interrupted
				35: Invalid
				36: Not start
				37: Queuing
				38: Stopped
				39: Copying
				40: Completed
				41: Paused
				42: Reverse synchronizing
				43: Activated
				44: Restore
				45: Inactive
				46: Idle
				47: Powering off
				48: Charging
				49: Charging completed
				50: Discharging
				51: Upgrading
				52: Power Lost
				53: Initializing
				54: Apply change
				55: Online disable
				56: Offline disable
				57: Online frozen
				58: Offline frozen
				59: Closed
				60: Removing
				61: In service
				62: Out of service
				63: Running normal
				64: Running fail
				65: Running success
				66: Running success
				67: Running failed
				68: Waiting
				69: Canceling
				70: Canceled
				71: About to synchronize
				72: Synchronizing data
				73: Failed to synchronize
				74: Fault
				75: Migrating
				76: Migrated
				77: Activating
				78: Deactivating
				79: Start failed
				80: Stop failed
				81: Decommissioning
				82: Decommissioned
				83: Recommissioning
				84: Replacing node
				85: Scheduling
				86: Pausing
				87: Suspending
				88: Suspended
				89: Overload
				90: To be switch
				91: Switching
				92: To be cleanup
				93: Forced start
				94: Error
				95: Job completed
				96: Partition Migrating
				97: Mount
				98: Umount
				99: INSTALLING
				100: To Be Synchronized
				101: Connecting
				102: Service Switching
				103: Power-on failed
				104: REPAIRING
				105: abnormal
				106: Deleting
				107: Modifying
				108: Running(clearing data)
				109: Running(synchronizing data)
				110: Standby
				111: STOPPING
				112: RESTORE FAULT
				113: Cut Over
				114: Erasing
				115: Verifying
				119: Creating"
			::= { hwInfoLunEntry 10 }

		
		-- 1.3.6.1.4.1.34774.4.1.23.4.8.1.11
		hwInfoLunType OBJECT-TYPE
			SYNTAX Unsigned32
			MAX-ACCESS read-only
			STATUS current
			DESCRIPTION
				"LUN type. The value can be:
				0: thick LUN
				1: thin LUN"
			::= { hwInfoLunEntry 11 }

		
		-- 1.3.6.1.4.1.34774.4.1.23.4.8.1.12
		hwInfoLunIOPriority OBJECT-TYPE
			SYNTAX Unsigned32
			MAX-ACCESS read-only
			STATUS current
			DESCRIPTION
				"I/O priority of the LUN. The value can be:
				1: low
				2: middle
				3: high"
			::= { hwInfoLunEntry 12 }

		
		-- 1.3.6.1.4.1.34774.4.1.23.4.8.1.13
		hwInfoLunWWN OBJECT-TYPE
			SYNTAX OCTET STRING
			MAX-ACCESS read-only
			STATUS current
			DESCRIPTION
				"WWN of the LUN."
			::= { hwInfoLunEntry 13 }

		
		-- 1.3.6.1.4.1.34774.4.1.23.4.8.1.14
		hwInfoLunExposedToInitiator OBJECT-TYPE
			SYNTAX Unsigned32
			MAX-ACCESS read-only
			STATUS current
			DESCRIPTION
				"Whether the LUN is mapped to an initiator. The value can be:
				0: no
				1: yes"
			::= { hwInfoLunEntry 14 }

		
		-- 1.3.6.1.4.1.34774.4.1.23.4.8.1.15
		hwInfoLunWritePolicy OBJECT-TYPE
			SYNTAX Unsigned32
			MAX-ACCESS read-only
			STATUS current
			DESCRIPTION
				"Cache write policy of the LUN. The value can be:
				1: write back
				2: write through
				3: forcible write back
				4: hybrid"
			::= { hwInfoLunEntry 15 }

		
		-- 1.3.6.1.4.1.34774.4.1.23.4.8.1.16
		hwInfoLunRunningWritePolicy OBJECT-TYPE
			SYNTAX Unsigned32
			MAX-ACCESS read-only
			STATUS current
			DESCRIPTION
				"Operating cache write policy of the LUN. The value can be:
				1: write back
				2: write through
				3: forcible write back
				4: hybrid"
			::= { hwInfoLunEntry 16 }

		
		-- 1.3.6.1.4.1.34774.4.1.23.4.8.1.17
		hwInfoLunPrefetchPolicy OBJECT-TYPE
			SYNTAX Unsigned32
			MAX-ACCESS read-only
			STATUS current
			DESCRIPTION
				"Cache prefetch policy of the LUN. The value can be:
				0: non-prefetch
				1: constant prefetch
				2: variable prefetch
				3: intelligent prefetch"
			::= { hwInfoLunEntry 17 }

		-- 1.3.6.1.4.1.34774.4.1.23.4.8.1.20
		hwInfoLunPrefetchValue OBJECT-TYPE
			SYNTAX Unsigned32
			MAX-ACCESS read-only
			STATUS current
			DESCRIPTION
				"Cache prefetch value of the LUN. The cache prefech policy can be:
				1. constant prefetch (unit: KB)
				2. variable prefetch (unit: times)
				3. non-prefetch or intelligent prefetch. 
				If 4294967295 is returned, the value is invalid."
			::= { hwInfoLunEntry 20 }

		
		-- 1.3.6.1.4.1.34774.4.1.23.4.8.1.21
		hwInfoLunOwnerController OBJECT-TYPE
			SYNTAX OCTET STRING
			MAX-ACCESS read-only
			STATUS current
			DESCRIPTION
				"Owning controller of the LUN."
			::= { hwInfoLunEntry 21 }

		
		-- 1.3.6.1.4.1.34774.4.1.23.4.8.1.22
		hwInfoLunWorkController OBJECT-TYPE
			SYNTAX OCTET STRING
			MAX-ACCESS read-only
			STATUS current
			DESCRIPTION
				"Working controller of the LUN."
			::= { hwInfoLunEntry 22 }

		
--       1.3.6.1.4.1.34774.4.1.23.4.8.1.25
-- 1.3.6.1.4.1.34774.4.1.23.4.8.1.25
-- 1.3.6.1.4.1.34774.4.1.23.4.8.1.25
-- 1.3.6.1.4.1.34774.4.1.23.4.8.1.25
-- 1.3.6.1.4.1.34774.4.1.23.4.8.1.25
		-- 1.3.6.1.4.1.34774.4.1.23.4.8.1.25
		hwInfoLunIsAddToLunGroup OBJECT-TYPE
			SYNTAX Unsigned32
			MAX-ACCESS read-only
			STATUS current
			DESCRIPTION
				"Whether the LUN is added to the LUN group. The value can be:
				0: no
				1: yes"
			::= { hwInfoLunEntry 25 }

		
		-- 1.3.6.1.4.1.34774.4.1.23.4.8.1.26
		hwInfoLunDIFSwitch OBJECT-TYPE
			SYNTAX Unsigned32
			MAX-ACCESS read-only
			STATUS current
			DESCRIPTION
				"Whether the DIF function is enabled for the LUN. The value can be:
				0: no
				1: yes"
			::= { hwInfoLunEntry 26 }

		
		-- 1.3.6.1.4.1.34774.4.1.23.4.8.1.27
		hwInfoLunRemoteLUNWWN OBJECT-TYPE
			SYNTAX OCTET STRING
			MAX-ACCESS read-only
			STATUS current
			DESCRIPTION
				"WWN of the remote LUN."
			::= { hwInfoLunEntry 27 }

		
		-- 1.3.6.1.4.1.34774.4.1.23.4.8.1.28
		hwInfoLunUsageType OBJECT-TYPE
			SYNTAX Unsigned32
			MAX-ACCESS read-only
			STATUS current
			DESCRIPTION
				"LUN type. The value can be:
				0: internal LUN
				1: external LUN
				2: VVOL LUN
				3: PE LUN"
			::= { hwInfoLunEntry 28 }

		
--       1.6
-- 1.6
-- 1.6
-- 1.6
-- 1.6
-- 1.6
		isoConformance OBJECT IDENTIFIER ::= { iso 6 }

		
--       1.6.1
-- 1.6.1
-- 1.6.1
-- 1.6.1
-- 1.6.1
-- 1.6.1
		isoGroups OBJECT IDENTIFIER ::= { isoConformance 1 }

		
--       1.6.1.1
-- 1.6.1.1
-- 1.6.1.1
-- 1.6.1.1
-- 1.6.1.1
-- 1.6.1.1
		currentObjectGroup OBJECT-GROUP
			OBJECTS { hwInfoDiskDomainID, hwInfoDiskDomainName, hwInfoDiskDomainHealthStatus, hwInfoDiskDomainRunningStatus, hwInfoDiskDomainTotalCapacity, 
				hwInfoDiskDomainFreeCapacity, hwInfoDiskDomainHotSpareCapacity, hwInfoDiskDomainUsedHotSpareCapacity, hwInfoStoragePoolID, hwInfoStoragePoolName, 
				hwInfoStoragePoolDiskDomainID, hwInfoStoragePoolHealthStatus, hwInfoStoragePoolRunningStatus, hwInfoStoragePoolTotalCapacity, hwInfoStoragePoolSubscribedCapacity, 
				hwInfoStoragePoolFreeCapacity, hwInfoStoragePoolFullThreshold, hwInfoHostID, hwInfoHostName, hwInfoHostLocation, 
				hwInfoHostHealthStatus, hwInfoHostRunningStatus, hwInfoHostOperatingSystem, hwInfoHostIPAddress, hwInfoHostModel, 
				hwInfoHostNetworkName, hwInfoHostGroupID, hwInfoHostGroupName, hwInfoLunGroupID, hwInfoLunGroupName, 
				hwInfoLunID, hwInfoLunName, hwInfoLunPoolID, hwInfoLunPoolName, hwInfoLunCapacity, 
				hwInfoLunSubscribedCapacity, hwInfoLunProtectionCapacity, hwInfoLunSectorSize, hwInfoLunHealthStatus, hwInfoLunRunningStatus, 
				hwInfoLunType, hwInfoLunIOPriority, hwInfoLunWWN, hwInfoLunExposedToInitiator, hwInfoLunWritePolicy, 
				hwInfoLunRunningWritePolicy, hwInfoLunPrefetchPolicy, hwInfoLunPrefetchValue, hwInfoLunOwnerController, hwInfoLunWorkController, 
				hwInfoLunIsAddToLunGroup, hwInfoLunDIFSwitch, hwInfoLunRemoteLUNWWN, hwInfoStoragePoolDiskDomainName, hwInfoPortGroupID, 
				hwInfoPortGroupName, hwInfoPortGroupPortList, hwInfoHostGroupHostList, hwInfoLunGroupLunList, hwInfoStoragePoolLunTotalCapacity, 
				hwInfoStoragePoolDataReductionRatio, hwInfoStoragePoolDeduplicationRatio, hwInfoStoragePoolCompressionRatio, hwInfoLunUsageType, hwInfoStoragePoolProtectionCapacity
				 }
			STATUS current
			DESCRIPTION 
				"Enter the description of the created OBJECT-GROUP."
			::= { isoGroups 1 }

		
--       1.6.2
-- 1.6.2
-- 1.6.2
-- 1.6.2
-- 1.6.2
-- 1.6.2
		isoCompliances OBJECT IDENTIFIER ::= { isoConformance 2 }

		
--        this module
-- 1.6.2.1
-- this module
-- 1.6.2.1
-- this module
-- 1.6.2.1
-- this module
-- 1.6.2.1
-- this module
-- 1.6.2.1
-- this module
-- 1.6.2.1
-- this module
		basicCompliance MODULE-COMPLIANCE
			STATUS current
			DESCRIPTION 
				"Enter the description of the created MODULE-COMPLIANCE."
			MODULE -- this module
				MANDATORY-GROUPS { currentObjectGroup }
			::= { isoCompliances 1 }

		
	
	END

--
-- HUAWEI-STORAGE-SPACE-MIB.mib
--
