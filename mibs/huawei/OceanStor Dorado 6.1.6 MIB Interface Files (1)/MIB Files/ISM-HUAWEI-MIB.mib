--
-- ISM-HUAWEI-MIB.mib
-- MIB generated by MG-SOFT Visual MIB Builder Version 4.0 Build 347
-- Thursday, March 27, 2014 at 11:36:30
--

	ISM-HUAWEI-MIB DEFINITIONS ::= BEGIN
 
		IMPORTS
			OBJECT-GROUP, MODULE-COMPLIANCE, NOTIFICATION-GROUP			
				FROM SNMPv2-CONF			
			enterprises, IpAddress, Integer32, Gauge32, 
			Counter64, OBJECT-TYPE, MODULE-IDENTITY, OBJECT-IDENTITY, NOTIFICATION-TYPE			
				FROM SNMPv2-SMI			
			DisplayString, DateAndTime, RowStatus, TEXTUAL-CONVENTION			
				FROM SNMPv2-TC;
	
	
		-- 1.3.6.1.4.1.2011.2.91
		hwISMCommon MODULE-IDENTITY 
			LAST-UPDATED "201303061010Z"		-- March 06, 2013 at 10:10 GMT
			ORGANIZATION 
				"Huawei Technologies Co.,Ltd."
			CONTACT-INFO 
				"Huawei Industrial Base
				Bantian, Longgang
				Shenzhen 518129
				People's Republic of China
				Website: http://www.huawei.com
				Email: support@huawei.com"
			DESCRIPTION 
				"The ISM-HUAWEI-MIB contains objects to query the basis device information."
			REVISION "200809171629Z"		-- September 17, 2008 at 16:29 GMT
			DESCRIPTION 
				"V1R1
				V1R2"
			::= { products 91 }

		
	
--
-- Textual conventions
--
	
		NodeCodeString ::= TEXTUAL-CONVENTION
			DISPLAY-HINT 
				"255a"
			STATUS current
			DESCRIPTION 
				"characters in length."
			SYNTAX OCTET STRING (SIZE (15..17))

	
--
-- Node definitions
--
	
		-- 1.3.6.1.4.1.2011
		huawei OBJECT IDENTIFIER ::= { enterprises 2011 }

		
		-- 1.3.6.1.4.1.2011.2
		products OBJECT IDENTIFIER ::= { huawei 2 }

		
		-- 1.3.6.1.4.1.2011.2.91.9
		hwIsmTopo OBJECT IDENTIFIER ::= { hwISMCommon 9 }

		
		-- 1.3.6.1.4.1.2011.2.91.9.1
		hwIsmAccessNodeInfo OBJECT IDENTIFIER ::= { hwIsmTopo 1 }

		
		-- 1.3.6.1.4.1.2011.2.91.9.1.1
		hwIsmAccessNodeTable OBJECT-TYPE
			SYNTAX SEQUENCE OF HwIsmAccessNodeEntry
			MAX-ACCESS not-accessible
			STATUS current
			DESCRIPTION
				"This table gives basis device information."
			::= { hwIsmAccessNodeInfo 1 }

		
		-- 1.3.6.1.4.1.2011.2.91.9.1.1.1
		hwIsmAccessNodeEntry OBJECT-TYPE
			SYNTAX HwIsmAccessNodeEntry
			MAX-ACCESS not-accessible
			STATUS current
			DESCRIPTION
				"A table containing the part component."
			INDEX { hwIsmNENodeCode }
			::= { hwIsmAccessNodeTable 1 }

		
		HwIsmAccessNodeEntry ::=
			SEQUENCE { 
				hwIsmNENodeCode
					OCTET STRING,
				hwIsmNENodeType
					Integer32,
				hwIsmNENodeWorkingMode
					INTEGER,
				hwIsmNENodeIPAddress
					IpAddress,
				hwIsmNENodeContextName
					DisplayString,
				hwIsmNENodeContextEngineID
					DisplayString,
				hwIsmNENodeClusterName
					DisplayString,
				hwIsmNENodeRunningStatus
					INTEGER
			 }

		-- 1.3.6.1.4.1.2011.2.91.9.1.1.1.1
		hwIsmNENodeCode OBJECT-TYPE
			SYNTAX OCTET STRING
			MAX-ACCESS read-only
			STATUS current
			DESCRIPTION
				"ID of an NE node."
			::= { hwIsmAccessNodeEntry 1 }

		
		-- 1.3.6.1.4.1.2011.2.91.9.1.1.1.2
		hwIsmNENodeType OBJECT-TYPE
			SYNTAX Integer32
			MAX-ACCESS read-only
			STATUS current
			DESCRIPTION
				"Type of an NE node."
			::= { hwIsmAccessNodeEntry 2 }

		
		-- 1.3.6.1.4.1.2011.2.91.9.1.1.1.3
		hwIsmNENodeWorkingMode OBJECT-TYPE
			SYNTAX INTEGER
				{
				mode1(1),
				mode2(2),
				mode3(3),
				mode4(4)
				}
			MAX-ACCESS read-only
			STATUS current
			DESCRIPTION
				"Working mode of an NE node, not used currently."
			::= { hwIsmAccessNodeEntry 3 }

		
		-- 1.3.6.1.4.1.2011.2.91.9.1.1.1.4
		hwIsmNENodeIPAddress OBJECT-TYPE
			SYNTAX IpAddress
			MAX-ACCESS read-only
			STATUS current
			DESCRIPTION
				"IP address of an NE node, not used currently."
			::= { hwIsmAccessNodeEntry 4 }

		
		-- 1.3.6.1.4.1.2011.2.91.9.1.1.1.5
		hwIsmNENodeContextName OBJECT-TYPE
			SYNTAX DisplayString
			MAX-ACCESS read-only
			STATUS current
			DESCRIPTION
				"Name of the context."
			::= { hwIsmAccessNodeEntry 5 }

		
		-- 1.3.6.1.4.1.2011.2.91.9.1.1.1.6
		hwIsmNENodeContextEngineID OBJECT-TYPE
			SYNTAX DisplayString
			MAX-ACCESS read-only
			STATUS current
			DESCRIPTION
				"Engine ID of the context, not used currently."
			::= { hwIsmAccessNodeEntry 6 }

		
		-- 1.3.6.1.4.1.2011.2.91.9.1.1.1.7
		hwIsmNENodeClusterName OBJECT-TYPE
			SYNTAX DisplayString
			MAX-ACCESS read-only
			STATUS current
			DESCRIPTION
				"Name of the NE cluster, not used currently."
			::= { hwIsmAccessNodeEntry 7 }

		
		-- 1.3.6.1.4.1.2011.2.91.9.1.1.1.8
		hwIsmNENodeRunningStatus OBJECT-TYPE
			SYNTAX INTEGER
				{
				admin(1),
				freedom(2)
				}
			MAX-ACCESS read-only
			STATUS current
			DESCRIPTION
				"Running status of an NE:
				1. The SNMP agent communicates correctly with the device.
				2. The SNMP agent fails to communicate with the device.
				Not used currently."
			::= { hwIsmAccessNodeEntry 8 }

		
		-- 1.3.6.1.4.1.2011.2.91.10
		hwIsmNotification OBJECT IDENTIFIER ::= { hwISMCommon 10 }

		
		-- 1.3.6.1.4.1.2011.2.91.10.1
		hwIsmActiveAlarmInfo OBJECT IDENTIFIER ::= { hwIsmNotification 1 }

		
		-- 1.3.6.1.4.1.2011.2.91.10.1.1
		hwIsmActiveAlarmInfoTable OBJECT-TYPE
			SYNTAX SEQUENCE OF HwIsmActiveAlarmInfoEntry
			MAX-ACCESS not-accessible
			STATUS current
			DESCRIPTION
				"This table saves active alarms, which can be queried by the NMS."
			::= { hwIsmActiveAlarmInfo 1 }

		
		-- 1.3.6.1.4.1.2011.2.91.10.1.1.1
		hwIsmActiveAlarmInfoEntry OBJECT-TYPE
			SYNTAX HwIsmActiveAlarmInfoEntry
			MAX-ACCESS not-accessible
			STATUS current
			DESCRIPTION
				"A table containing the part component."
			INDEX { hwIsmActiveAlarmInfoNodeCode, hwIsmActiveAlarmInfoSerialNo }
			::= { hwIsmActiveAlarmInfoTable 1 }

		
		HwIsmActiveAlarmInfoEntry ::=
			SEQUENCE { 
				hwIsmActiveAlarmInfoNodeCode
					NodeCodeString,
				hwIsmActiveAlarmInfoLocationInfo
					DisplayString,
				hwIsmActiveAlarmInfoRestoreAdvice
					DisplayString,
				hwIsmActiveAlarmInfoTitle
					DisplayString,
				hwIsmActiveAlarmInfoType
					INTEGER,
				hwIsmActiveAlarmInfoLevel
					INTEGER,
				hwIsmActiveAlarmInfoAlarmID
					Gauge32,
				hwIsmActiveAlarmInfoOccurTime
					DateAndTime,
				hwIsmActiveAlarmInfoSerialNo
					Gauge32,
				hwIsmActiveAlarmInfoAddtionInfo
					OCTET STRING,
				hwIsmActiveAlarmInfoCategory
					INTEGER,
				hwIsmActiveAlarmInfoLocalAlarmID
					Counter64
			 }

		-- 1.3.6.1.4.1.2011.2.91.10.1.1.1.1
		hwIsmActiveAlarmInfoNodeCode OBJECT-TYPE
			SYNTAX NodeCodeString
			MAX-ACCESS read-only
			STATUS current
			DESCRIPTION
				"ID of the node where an alarm occurs."
			::= { hwIsmActiveAlarmInfoEntry 1 }

		
		-- 1.3.6.1.4.1.2011.2.91.10.1.1.1.2
		hwIsmActiveAlarmInfoLocationInfo OBJECT-TYPE
			SYNTAX DisplayString
			MAX-ACCESS read-only
			STATUS current
			DESCRIPTION
				"Alarm location information. The format is: Name1 = Value1, …, NameN = ValueN"
			::= { hwIsmActiveAlarmInfoEntry 2 }

		
		-- 1.3.6.1.4.1.2011.2.91.10.1.1.1.3
		hwIsmActiveAlarmInfoRestoreAdvice OBJECT-TYPE
			SYNTAX DisplayString
			MAX-ACCESS read-only
			STATUS current
			DESCRIPTION
				"Alarm handling suggestion."
			::= { hwIsmActiveAlarmInfoEntry 3 }

		
		-- 1.3.6.1.4.1.2011.2.91.10.1.1.1.4
		hwIsmActiveAlarmInfoTitle OBJECT-TYPE
			SYNTAX DisplayString
			MAX-ACCESS read-only
			STATUS current
			DESCRIPTION
				"Alarm information title."
			::= { hwIsmActiveAlarmInfoEntry 4 }

		
		-- 1.3.6.1.4.1.2011.2.91.10.1.1.1.5
		hwIsmActiveAlarmInfoType OBJECT-TYPE
			SYNTAX INTEGER { equipmentFault(2) }
			MAX-ACCESS read-only
			STATUS current
			DESCRIPTION
				"Alarm type: 2-EquipmentAlarm"
			::= { hwIsmActiveAlarmInfoEntry 5 }

		
		-- 1.3.6.1.4.1.2011.2.91.10.1.1.1.6
		hwIsmActiveAlarmInfoLevel OBJECT-TYPE
			SYNTAX INTEGER
				{
				criticalAlarm(1),
				majorAlarm(2),
				minorAlarm(3),
				warningAlarm(4)
				}
			MAX-ACCESS read-only
			STATUS current
			DESCRIPTION
				"Alarm severity of I2000 network management software:
				1-criticalAlarm
				2-majorAlarm
				3-minorAlarm
				4-warningAlarm"
			::= { hwIsmActiveAlarmInfoEntry 6 }

		
		-- 1.3.6.1.4.1.2011.2.91.10.1.1.1.7
		hwIsmActiveAlarmInfoAlarmID OBJECT-TYPE
			SYNTAX Gauge32
			MAX-ACCESS read-only
			STATUS current
			DESCRIPTION
				"Alarm ID of I2000 network management software."
			::= { hwIsmActiveAlarmInfoEntry 7 }

		
		-- 1.3.6.1.4.1.2011.2.91.10.1.1.1.8
		hwIsmActiveAlarmInfoOccurTime OBJECT-TYPE
			SYNTAX DateAndTime
			MAX-ACCESS read-only
			STATUS current
			DESCRIPTION
				"Time when an alarm was generated."
			::= { hwIsmActiveAlarmInfoEntry 8 }

		
		-- 1.3.6.1.4.1.2011.2.91.10.1.1.1.9
		hwIsmActiveAlarmInfoSerialNo OBJECT-TYPE
			SYNTAX Gauge32
			MAX-ACCESS read-only
			STATUS current
			DESCRIPTION
				"Alarm serial number (SN)."
			::= { hwIsmActiveAlarmInfoEntry 9 }

		
		-- 1.3.6.1.4.1.2011.2.91.10.1.1.1.10
		hwIsmActiveAlarmInfoAddtionInfo OBJECT-TYPE
			SYNTAX OCTET STRING
			MAX-ACCESS read-only
			STATUS current
			DESCRIPTION
				"Alarm cause."
			::= { hwIsmActiveAlarmInfoEntry 10 }

		
		-- 1.3.6.1.4.1.2011.2.91.10.1.1.1.11
		hwIsmActiveAlarmInfoCategory OBJECT-TYPE
			SYNTAX INTEGER
				{
				faultAlarm(1),
				resumeAlarm(2),
				eventAlarm(3)
				}
			MAX-ACCESS read-only
			STATUS current
			DESCRIPTION
				"Alarm category:
				1. -faultAlarm
				2. -resumeAlarm
				3. -eventAlarm"
			::= { hwIsmActiveAlarmInfoEntry 11 }

		
		-- 1.3.6.1.4.1.2011.2.91.10.1.1.1.12
		hwIsmActiveAlarmInfoLocalAlarmID OBJECT-TYPE
			SYNTAX Counter64
			MAX-ACCESS read-only
			STATUS current
			DESCRIPTION
				"Original alarm ID."
			::= { hwIsmActiveAlarmInfoEntry 12 }

		
		-- 1.3.6.1.4.1.2011.2.91.10.1.2
		hwIsmClearedAlarmConfirm OBJECT-TYPE
			SYNTAX Gauge32
			MAX-ACCESS read-write
			STATUS current
			DESCRIPTION
				"Confirmation of an active alarm.
				Set: Complete the SN of an active alarm. If the SN exists, clear this alarm and a clear alarm is reported. 
				If the SN does not exist, an error message is returned.
				Get: Returns a fixed value: 0, the value is meaningless."
			::= { hwIsmActiveAlarmInfo 2 }

		
		-- 1.3.6.1.4.1.2011.2.91.10.2
		hwIsmNotificationType OBJECT IDENTIFIER ::= { hwIsmNotification 2 }

		
		-- 1.3.6.1.4.1.2011.2.91.10.2.1
		hwinfoFaultNotificationType OBJECT IDENTIFIER ::= { hwIsmNotificationType 1 }

		
		-- 1.3.6.1.4.1.2011.2.91.10.2.1.0
		hwIsmFaultNotificationTypeV2 OBJECT-IDENTITY
			STATUS current
			DESCRIPTION 
				"Root node for the converted TRAP-TYPEs."
			::= { hwinfoFaultNotificationType 0 }

		
		-- 1.3.6.1.4.1.2011.2.91.10.2.1.0.1
		hwIsmAlarmReporting NOTIFICATION-TYPE
			OBJECTS { hwIsmReportingAlarmNodeCode, hwIsmReportingAlarmLocationInfo, hwIsmReportingAlarmRestoreAdvice, hwIsmReportingAlarmFaultTitle, hwIsmReportingAlarmFaultType, 
				hwIsmReportingAlarmFaultLevel, hwIsmReportingAlarmAlarmID, hwIsmReportingAlarmFaultTime, hwIsmReportingAlarmSerialNo, hwIsmReportingAlarmLocationAlarmID, hwIsmReportingAlarmProductModel,hwIsmReportingAlarmProductSN,
				hwIsmReportingAlarmFaultCategory, hwIsmReportingAlarmAdditionInfo }
			STATUS current
			DESCRIPTION 
				"The node is used for reporting the parsed alarm."
			::= { hwIsmFaultNotificationTypeV2 1 }

		
		-- 1.3.6.1.4.1.2011.2.91.10.3
		hwIsmTrapNotification OBJECT IDENTIFIER ::= { hwIsmNotification 3 }

		
		-- 1.3.6.1.4.1.2011.2.91.10.3.1
		hwIsmFaultNotification OBJECT IDENTIFIER ::= { hwIsmTrapNotification 1 }

		
		-- 1.3.6.1.4.1.2011.2.91.10.3.1.1
		hwIsmReportingAlarm OBJECT IDENTIFIER ::= { hwIsmFaultNotification 1 }

		-- 1.3.6.1.4.1.2011.2.91.10.3.1.1.1
		hwIsmReportingAlarmNodeCode OBJECT-TYPE
			SYNTAX NodeCodeString
			MAX-ACCESS accessible-for-notify
			STATUS current
			DESCRIPTION
				"ID of the node where an alarm occurs."
			REFERENCE
				"Location info of  Fault Alarm"
			::= { hwIsmReportingAlarm 1 }

		
		-- 1.3.6.1.4.1.2011.2.91.10.3.1.1.2
		hwIsmReportingAlarmLocationInfo OBJECT-TYPE
			SYNTAX DisplayString
			MAX-ACCESS accessible-for-notify
			STATUS current
			DESCRIPTION
				"Alarm location information. The format is: Name1 = Value1, …, NameN = ValueN."
			::= { hwIsmReportingAlarm 2 }

		
		-- 1.3.6.1.4.1.2011.2.91.10.3.1.1.3
		hwIsmReportingAlarmRestoreAdvice OBJECT-TYPE
			SYNTAX OCTET STRING (SIZE (0..256))
			MAX-ACCESS accessible-for-notify
			STATUS current
			DESCRIPTION
				"Alarm handling suggestion."
			::= { hwIsmReportingAlarm 3 }

		
		-- 1.3.6.1.4.1.2011.2.91.10.3.1.1.4
		hwIsmReportingAlarmFaultTitle OBJECT-TYPE
			SYNTAX OCTET STRING (SIZE (0..256))
			MAX-ACCESS accessible-for-notify
			STATUS current
			DESCRIPTION
				"Alarm information title."
			::= { hwIsmReportingAlarm 4 }

		
		-- 1.3.6.1.4.1.2011.2.91.10.3.1.1.5
		hwIsmReportingAlarmFaultType OBJECT-TYPE
			SYNTAX INTEGER
				{
				communicationQuality(1),
				equipmentFault(2),
				eventAlarm(3),
				serviceQuality(4),
				environmentFault(5),
				performanceLimit(6)
				}
			MAX-ACCESS accessible-for-notify
			STATUS current
			DESCRIPTION
				"Alarm type:
				2-EquipmentAlarm
				3-EventAlarm"
			::= { hwIsmReportingAlarm 5 }

		
		-- 1.3.6.1.4.1.2011.2.91.10.3.1.1.6
		hwIsmReportingAlarmFaultLevel OBJECT-TYPE
			SYNTAX INTEGER
				{
				criticalAlarm(1),
				majorAlarm(2),
				minorAlarm(3),
				warningAlarm(4),
				eventAlarm(5)
				}
			MAX-ACCESS accessible-for-notify
			STATUS current
			DESCRIPTION
				"Alarm severity of I2000 network management	software:
				1-criticalAlarm
				2-majorAlarm
				3-minorAlarm
				4-warningAlarm
				5-eventAlarm"
			::= { hwIsmReportingAlarm 6 }

		
		-- 1.3.6.1.4.1.2011.2.91.10.3.1.1.7
		hwIsmReportingAlarmAlarmID OBJECT-TYPE
			SYNTAX Gauge32
			MAX-ACCESS accessible-for-notify
			STATUS current
			DESCRIPTION
				"Alarm ID of I2000 network management software."
			::= { hwIsmReportingAlarm 7 }

		
		-- 1.3.6.1.4.1.2011.2.91.10.3.1.1.8
		hwIsmReportingAlarmFaultTime OBJECT-TYPE
			SYNTAX DateAndTime
			MAX-ACCESS accessible-for-notify
			STATUS current
			DESCRIPTION
				"Time when an alarm was generated."
			::= { hwIsmReportingAlarm 8 }

		

		-- 1.3.6.1.4.1.2011.2.91.10.3.1.1.9
		hwIsmReportingAlarmSerialNo OBJECT-TYPE
			SYNTAX Gauge32
			MAX-ACCESS accessible-for-notify
			STATUS current
			DESCRIPTION
				"Alarm serial number(SN)"
			::= { hwIsmReportingAlarm 9 }

		

		-- 1.3.6.1.4.1.2011.2.91.10.3.1.1.10
		hwIsmReportingAlarmAdditionInfo OBJECT-TYPE
			SYNTAX DisplayString
			MAX-ACCESS accessible-for-notify
			STATUS current
			DESCRIPTION
				"Alarm cause."
			::= { hwIsmReportingAlarm 10 }

		

		-- 1.3.6.1.4.1.2011.2.91.10.3.1.1.11
		hwIsmReportingAlarmFaultCategory OBJECT-TYPE
			SYNTAX INTEGER
				{
				faultAlarm(1),
				resumeAlarm(2),
				eventAlarm(3)
				}
			MAX-ACCESS accessible-for-notify
			STATUS current
			DESCRIPTION
				"Alarm category:
				1-faultAlarm
				2-resumeAlarm
				3-eventAlarm"
			::= { hwIsmReportingAlarm 11 }

		

		-- 1.3.6.1.4.1.2011.2.91.10.3.1.1.12
		hwIsmReportingAlarmLocationAlarmID OBJECT-TYPE
			SYNTAX Counter64
			MAX-ACCESS accessible-for-notify
			STATUS current
			DESCRIPTION
				"Original alarm ID."
			::= { hwIsmReportingAlarm 12 }

		

		-- 1.3.6.1.4.1.2011.2.91.10.3.1.1.13
		hwIsmReportingAlarmProductModel OBJECT-TYPE
			SYNTAX Integer32
			MAX-ACCESS accessible-for-notify
			STATUS current
			DESCRIPTION
				"Product Model."
			::= { hwIsmReportingAlarm 13 }

		

		-- 1.3.6.1.4.1.2011.2.91.10.3.1.1.14
		hwIsmReportingAlarmProductSN OBJECT-TYPE
			SYNTAX OCTET STRING
			MAX-ACCESS accessible-for-notify
			STATUS current
			DESCRIPTION
				"SN."
			::= { hwIsmReportingAlarm 14 }
		
		-- 1.3.6.1.4.1.2011.2.91.10.4
		hwIsmTrapForwardControl OBJECT IDENTIFIER ::= { hwIsmNotification 4 }

		
		-- 1.3.6.1.4.1.2011.2.91.10.4.1
		hwIsmTrapTargetAddrTable OBJECT-TYPE
			SYNTAX SEQUENCE OF HwIsmTrapTargetAddrEntry
			MAX-ACCESS not-accessible
			STATUS current
			DESCRIPTION
				"This table gives information about alarm forwarding addresses, involving IP addresses, ports, and versions."
			::= { hwIsmTrapForwardControl 1 }

		

		-- 1.3.6.1.4.1.2011.2.91.10.4.1.1
		hwIsmTrapTargetAddrEntry OBJECT-TYPE
			SYNTAX HwIsmTrapTargetAddrEntry
			MAX-ACCESS not-accessible
			STATUS current
			DESCRIPTION
				"A table containing the part component."
			INDEX { hwIsmTrapTargetAddrIndex }
			::= { hwIsmTrapTargetAddrTable 1 }

		
		HwIsmTrapTargetAddrEntry ::=
			SEQUENCE { 
				hwIsmTrapTargetAddrIPAddr
					IpAddress,
				hwIsmTrapTargetAddrPort
					Integer32,
				hwIsmTrapTargetAddrRowStatus
					RowStatus,
				hwIsmTrapTargetAddrIndex
					OCTET STRING,
				hwIsmTrapTargetAddrTrapVer
					Integer32,
				hwIsmTrapTargetAddrIPAddrNew
					OCTET STRING,
				hwIsmTrapTargetAddrTrapType
					Integer32,
				hwIsmTrapTargetAddrUSMUserName
					OCTET STRING
			 }


		-- 1.3.6.1.4.1.2011.2.91.10.4.1.1.1
		hwIsmTrapTargetAddrIPAddr OBJECT-TYPE
			SYNTAX IpAddress
			MAX-ACCESS read-create
			STATUS current
			DESCRIPTION
				"Destination address for trap forwarding. Only support IPv4 format."
			::= { hwIsmTrapTargetAddrEntry 1 }

		

		-- 1.3.6.1.4.1.2011.2.91.10.4.1.1.2
		hwIsmTrapTargetAddrPort OBJECT-TYPE
			SYNTAX Integer32
			MAX-ACCESS read-create
			STATUS current
			DESCRIPTION
				"Port of the destination address for trap forwarding. The value can be 1 to 65535."
			::= { hwIsmTrapTargetAddrEntry 2 }

		

		-- 1.3.6.1.4.1.2011.2.91.10.4.1.1.3
		hwIsmTrapTargetAddrRowStatus OBJECT-TYPE
			SYNTAX RowStatus
			MAX-ACCESS read-create
			STATUS current
			DESCRIPTION
				"Row status. The value can be:
				1: Modify the Trap forwarding destination address
				4: Add the Trap forwarding destination address
				6: Delete the Trap forwarding destination address"
			::= { hwIsmTrapTargetAddrEntry 3 }

		

		-- 1.3.6.1.4.1.2011.2.91.10.4.1.1.4
		hwIsmTrapTargetAddrIndex OBJECT-TYPE
			SYNTAX OCTET STRING
			MAX-ACCESS read-create
			STATUS current
			DESCRIPTION
				"Index of the destination address for trap forwarding. The value can be 0 to 3."
			::= { hwIsmTrapTargetAddrEntry 4 }


		-- 1.3.6.1.4.1.2011.2.91.10.4.1.1.5
		hwIsmTrapTargetAddrTrapVer OBJECT-TYPE
			SYNTAX Integer32
			MAX-ACCESS read-create
			STATUS current
			DESCRIPTION
				"Version of the destination address for trap forwarding. The value can be:
				1: SNMPv1
				2: SNMPv2c
				3: SNMPv3
				When configuring the destination address for trap forwarding, if this field is not filled, the default is SNMPv2c."
			::= { hwIsmTrapTargetAddrEntry 5 }

		
		-- 1.3.6.1.4.1.2011.2.91.10.4.1.1.6
		hwIsmTrapTargetAddrIPAddrNew OBJECT-TYPE
			SYNTAX OCTET STRING
			MAX-ACCESS read-create
			STATUS current
			DESCRIPTION
				"New destination address for trap forwarding. IP addresses in the IPv4 or IPv6 format, and IP address in the domain name format are supported. If hwIsmTrapTargetAddrIPAddr and hwIsmTrapTargetAddrIPAddrNew fields are filled with values, take the value of the hwIsmTrapTargetAddrIPAddrNew fields by default. The domain name address is not configured on the DNS server or the network delays, leading to the timeout of the message returned by the network management software. Adjust the timeout period setting based on the network environment."
			::= { hwIsmTrapTargetAddrEntry 6 }

		
		-- 1.3.6.1.4.1.2011.2.91.10.4.1.1.7
		hwIsmTrapTargetAddrTrapType OBJECT-TYPE
			SYNTAX Integer32
			MAX-ACCESS read-create
			STATUS current
			DESCRIPTION
				"Type of the destination address for trap forwarding. The value can be:
				 1: Parsed. Sends parsed alarms to the destination address for trap forwarding (Trap OID: 1.3.6.1.4.1.2011.2.91.10.2.1.0.1).
				 2: Original. Sends original alarms to the destination address for trap forwarding (Trap OID: 1.3.6.1.4.1.34774.4.1.4.2).
				 3: All. sends Parsed, Original, and Parsed_alarm_oid alarms to the destination address for trap forwarding.
				 4: Parsed_alarm_oid. Sends parsed alarms to the destination address for trap forwarding (Each alarm corresponds to one OID. Products later than V3R6 support the alarm OID).
				 5: Parsed_time_string. Sends parsed alarms to the destination address for trap forwarding (Products V3R3C20SPC200 and later than V3R6 support this trap type. Trap OID: 1.3.6.1.4.1.2011.2.251.20.1.2.1).
				 6: Original_time_string.Sends original alarms to the destination address for trap forwarding (Products V3R3C20SPC200 andlater than V3R6 support this trap type. Trap OID: 1.3.6.1.4.1.2011.2.251.20.2.1.1).
				When configuring the destination address for trap forwarding, if this field is not filled, the default is Parsed."
			::= { hwIsmTrapTargetAddrEntry 7 }

		
		-- 1.3.6.1.4.1.2011.2.91.10.4.1.1.8
		hwIsmTrapTargetAddrUSMUserName OBJECT-TYPE
			SYNTAX OCTET STRING
			MAX-ACCESS read-create
			STATUS current
			DESCRIPTION
				"USM user name of the destination address for trap forwarding. When the trap forwarding address type is SNMPv3, this field is mandatory and users must ensure a specified USM user exists in the system. Otherwise, this operation fails to be performed. If this field is mandatory, and the parameter is not delivered or no value is specified for the parameter, the system default value is Kaimse."
			::= { hwIsmTrapTargetAddrEntry 8 }

		
		isoConformance OBJECT IDENTIFIER ::= { iso 6 }

		
		isoGroups OBJECT IDENTIFIER ::= { isoConformance 1 }

		
		currentObjectGroup OBJECT-GROUP
			OBJECTS { hwIsmActiveAlarmInfoNodeCode, hwIsmActiveAlarmInfoLocationInfo, hwIsmActiveAlarmInfoRestoreAdvice, hwIsmActiveAlarmInfoTitle, hwIsmActiveAlarmInfoType, 
				hwIsmActiveAlarmInfoLevel, hwIsmActiveAlarmInfoAlarmID, hwIsmActiveAlarmInfoOccurTime, hwIsmActiveAlarmInfoSerialNo, hwIsmActiveAlarmInfoCategory, 
				hwIsmReportingAlarmNodeCode, hwIsmReportingAlarmLocationInfo, hwIsmReportingAlarmRestoreAdvice, hwIsmReportingAlarmFaultTitle, hwIsmReportingAlarmFaultType, 
				hwIsmReportingAlarmFaultLevel, hwIsmReportingAlarmAlarmID, hwIsmReportingAlarmFaultTime, hwIsmReportingAlarmSerialNo, hwIsmReportingAlarmFaultCategory, 
				hwIsmReportingAlarmAdditionInfo, hwIsmNENodeCode, hwIsmNENodeType, hwIsmNENodeIPAddress, hwIsmNENodeContextName, 
				hwIsmNENodeContextEngineID, hwIsmClearedAlarmConfirm, hwIsmActiveAlarmInfoAddtionInfo, hwIsmTrapTargetAddrIPAddr, hwIsmTrapTargetAddrPort, 
				hwIsmTrapTargetAddrRowStatus, hwIsmReportingAlarmLocationAlarmID, hwIsmActiveAlarmInfoLocalAlarmID,hwIsmReportingAlarmProductModel,hwIsmReportingAlarmProductSN, hwIsmTrapTargetAddrIndex, hwIsmTrapTargetAddrTrapVer, 
				hwIsmTrapTargetAddrIPAddrNew, hwIsmTrapTargetAddrTrapType, hwIsmTrapTargetAddrUSMUserName, hwIsmNENodeRunningStatus, hwIsmNENodeWorkingMode, 
				hwIsmNENodeClusterName }
			STATUS current
			DESCRIPTION 
				"Enter the description of the created OBJECT-GROUP."
			::= { isoGroups 1 }

		
		currentNotificationGroup NOTIFICATION-GROUP
			NOTIFICATIONS { hwIsmAlarmReporting }
			STATUS current
			DESCRIPTION 
				"Enter the description of the created NOTIFICATION-GROUP."
			::= { isoGroups 2 }

		
		isoCompliances OBJECT IDENTIFIER ::= { isoConformance 2 }

		
		basicCompliance MODULE-COMPLIANCE
			STATUS current
			DESCRIPTION 
				"Enter the description of the created MODULE-COMPLIANCE."
			MODULE -- this module
				MANDATORY-GROUPS { currentObjectGroup, currentNotificationGroup }
			::= { isoCompliances 1 }

		
	
	END

--
-- ISM-HUAWEI-MIB.mib
--
