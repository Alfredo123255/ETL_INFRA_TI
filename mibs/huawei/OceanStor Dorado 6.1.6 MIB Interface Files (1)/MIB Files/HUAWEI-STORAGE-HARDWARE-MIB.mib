--
-- HUAWEI-STORAGE-HARDWARE-MIB.mib
-- MIB generated by MG-SOFT Visual MIB Builder Version 3.0 Build 253
-- Sunday, June 12, 2016 at 19:31:04
--

--  HUAWEI-STORAGE-HARDWARE-MIB.mib
-- MIB generated by MG-SOFT Visual MIB Builder Version 4.0 Build 347
-- Friday, October 17, 2014 at 18:50:14
-- 

	HUAWEI-STORAGE-HARDWARE-MIB DEFINITIONS ::= BEGIN
 
		IMPORTS
			OBJECT-GROUP, MODULE-COMPLIANCE			
				FROM SNMPv2-CONF			
			enterprises, Integer32, Unsigned32, Counter64, 
			OBJECT-TYPE, MODULE-IDENTITY			
				FROM SNMPv2-SMI			
			TEXTUAL-CONVENTION			
				FROM SNMPv2-TC;
	
	
		hwStorage MODULE-IDENTITY 
			LAST-UPDATED "201008111239Z"		-- August 11, 2010 at 12:39 GMT
			ORGANIZATION 
				"Huawei Technologies Co.,Ltd."
			CONTACT-INFO 
				"Huawei Industrial Base
				Bantian, Longgang
				Shenzhen 518129
				People's Republic of China
				Website: http://www.huawei.com
				Email: support@huawei.com"
			DESCRIPTION 
				"The HUAWEI-STORAGE-HARDWARE-MIB contains objects of storage hardware modules."
			REVISION "201404061354Z"		-- April 06, 2014 at 13:54 GMT
			DESCRIPTION
				" "
			::= { huaweistorage 4 }
		
	
--
-- Textual conventions
--
	
--  August 11, 2010 at 12:39 GMT
-- April 06, 2014 at 13:54 GMT
-- 
-- Textual conventions
-- 
--  August 11, 2010 at 12:39 GMT
-- April 06, 2014 at 13:54 GMT
-- 
-- Textual conventions
-- 
		NodeCodeString ::= TEXTUAL-CONVENTION
			DISPLAY-HINT 
				"255a"
			STATUS current
			DESCRIPTION 
				"characters in length."
			SYNTAX OCTET STRING (SIZE (15..17))
			
	
--
-- Node definitions
--
	
--  Node definitions
-- 
		-- 1.3.6.1.4.1.34774
		huaweistorage OBJECT IDENTIFIER ::= { enterprises 34774 }
		
		-- 1.3.6.1.4.1.34774.4.1
		hwISM OBJECT IDENTIFIER ::= { hwStorage 1 }
		
		-- 1.3.6.1.4.1.34774.4.1.23
		hwStorageDevice OBJECT IDENTIFIER ::= { hwISM 23 }
		
		-- 1.3.6.1.4.1.34774.4.1.23.5
		hwHardwareInfo OBJECT IDENTIFIER ::= { hwStorageDevice 5 }
		
		-- 1.3.6.1.4.1.34774.4.1.23.5.1
		hwInfoDiskTable OBJECT-TYPE
			SYNTAX SEQUENCE OF HwInfoDiskEntry
			MAX-ACCESS not-accessible
			STATUS current
			DESCRIPTION
				"This table is used to check the disk information about a device."
			::= { hwHardwareInfo 1 }
		
		-- 1.3.6.1.4.1.34774.4.1.23.5.1.1
		hwInfoDiskEntry OBJECT-TYPE
			SYNTAX HwInfoDiskEntry
			MAX-ACCESS not-accessible
			STATUS current
			DESCRIPTION
				"A table containing the part component."
			INDEX { hwInfoDiskID }
			::= { hwInfoDiskTable 1 }
		
		HwInfoDiskEntry ::=
			SEQUENCE { 
				hwInfoDiskID
					OCTET STRING,
				hwInfoDiskHealthStatus
					Unsigned32,
				hwInfoDiskRunningStatus
					Unsigned32,
				hwInfoDiskLocation
					OCTET STRING,
				hwInfoDiskType
					Unsigned32,
				hwInfoDiskCapacity
					Counter64,
				hwInfoDiskRole
					Unsigned32,
				hwInfoDiskSpeed
					Unsigned32,
				hwInfoDiskInterfaceBandwidth
					Unsigned32,
				hwInfoDiskSectorSize
					Unsigned32,
				hwInfoDiskTemperature
					Integer32,
				hwInfoDiskModel
					OCTET STRING,
				hwInfoDiskFirmwareVersion
					OCTET STRING,
				hwInfoDiskManufacturer
					OCTET STRING,
				hwInfoDiskSerialNumber
					OCTET STRING,
				hwInfoDiskLightStatus
					Unsigned32,
				hwInfoDiskDiskDomainID
					OCTET STRING,
				hwInfoDiskDiskDomainName
					OCTET STRING,
				hwInfoDiskDiskDomainTierID
					OCTET STRING,
				hwInfoDiskCofferDisk
					Unsigned32,
				hwInfoDiskRunTime
					Unsigned32,
				hwInfoDiskProgress
					Unsigned32,
				hwInfoDiskBarCode
					OCTET STRING,
				hwInfoDiskCapacityUsage
					Unsigned32,
				hwInfoDiskHealthMark
					Unsigned32,
                hwInfoDiskElectronicLabel
                    OCTET STRING
			 }

		-- 1.3.6.1.4.1.34774.4.1.23.5.1.1.1
		hwInfoDiskID OBJECT-TYPE
			SYNTAX OCTET STRING
			MAX-ACCESS read-only
			STATUS current
			DESCRIPTION
				"Disk ID, table index."
			::= { hwInfoDiskEntry 1 }
		
		-- 1.3.6.1.4.1.34774.4.1.23.5.1.1.2
		hwInfoDiskHealthStatus OBJECT-TYPE
			SYNTAX Unsigned32
			MAX-ACCESS read-only
			STATUS current
			DESCRIPTION
				"Disk health status. For details, see:
				1 Normal
				2 Fault
				3 Pre-Fail
				4 Partially Broken
				5 Degraded
				6 Bad Sectors Found
				7 Bit Errors Found
				8 Consistent
				9 Inconsistent
				10 Busy
				11 No Input
				12 Low Battery
				13 Single Link Fault
				14 Invalid
				15 Write Protect
				16 single link
				17 No Redundant Link
				18 Offline"
			::= { hwInfoDiskEntry 2 }
		
		-- 1.3.6.1.4.1.34774.4.1.23.5.1.1.3
		hwInfoDiskRunningStatus OBJECT-TYPE
			SYNTAX Unsigned32
			MAX-ACCESS read-only
			STATUS current
			DESCRIPTION
				"Disk running status. For details, see:
				1: Normal
				2: Running
				3: Not running
				4: Not existed
				5: Sleep in high temperature
				6: Starting
				7: Power failure rotection
				8: Spin down
				9: Started
				10: Link Up
				11: Link Down
				12: Powering on
				13: Powered off
				14: Pre-copy
				15: Copyback
				16: Reconstruction
				17: Expansion
				18: Unformatted
				19: Formatting
				20: Unmapped
				21: Initial synchronizing
				22: Consistent
				23: Synchronizing
				24: Synchronized
				25: Unsynchronized
				26: Split
				27: Online
				28: Offline
				29: Locked
				30: Enabled
				31: Disabled
				32: Balancing
				33: To be recovered
				34: Interrupted
				35: Invalid
				36: Not start
				37: Queuing
				38: Stopped
				39: Copying
				40: Completed
				41: Paused
				42: Reverse synchronizing
				43: Activated
				44: Restore
				45: Inactive
				46: Idle
				47: Powering off
				48: Charging
				49: Charging completed
				50: Discharging
				51: Upgrading
				52: Power Lost
				53: Initializing
				54: Apply change
				55: Online disable
				56: Offline disable
				57: Online frozen
				58: Offline frozen
				59: Closed
				60: Removing
				61: In service
				62: Out of service
				63: Running normal
				64: Running fail
				65: Running success
				66: Running success
				67: Running failed
				68: Waiting
				69: Canceling
				70: Canceled
				71: About to synchronize
				72: Synchronizing data
				73: Failed to synchronize
				74: Fault
				75: Migrating
				76: Migrated
				77: Activating
				78: Deactivating
				79: Start failed
				80: Stop failed
				81: Decommissioning
				82: Decommissioned
				83: Recommissioning
				84: Replacing node
				85: Scheduling
				86: Pausing
				87: Suspending
				88: Suspended
				89: Overload
				90: To be switch
				91: Switching
				92: To be cleanup
				93: Forced start
				94: Error
				95: Job completed
				96: Partition Migrating
				97: Mount
				98: Umount
				99: INSTALLING
				100: To Be Synchronized
				101: Connecting
				102: Service Switching
				103: Power-on failed
				104: REPAIRING
				105: abnormal
				106: Deleting
				107: Modifying
				108: Running(clearing data)
				109: Running(synchronizing data)
				110: Standby
				111: STOPPING
				112: RESTORE FAULT
				113: Cut Over
				114: Erasing
				115: Verifying
				119: Creating"
			::= { hwInfoDiskEntry 3 }
		
		-- 1.3.6.1.4.1.34774.4.1.23.5.1.1.4
		hwInfoDiskLocation OBJECT-TYPE
			SYNTAX OCTET STRING
			MAX-ACCESS read-only
			STATUS current
			DESCRIPTION
				"Disk location."
			::= { hwInfoDiskEntry 4 }
		
		-- 1.3.6.1.4.1.34774.4.1.23.5.1.1.5
		hwInfoDiskType OBJECT-TYPE
			SYNTAX Unsigned32
			MAX-ACCESS read-only
			STATUS current
			DESCRIPTION
				"Disk type. Possible values are:
				0: FC
				1: SAS
				2: SATA
				3: SSD
				4: NL_SAS
				5: SLC SSD
				6: MLC SSD
				7:FC_SED
				8:SAS_SED
				9:SATA_SED
				10:SSD_SED
				11:NL_SAS_SED
				12:SLC_SSD_SED
				13:MLC_SSD_SED
				14:NVMe_SSD
				15:SMR_SATA
				16:NVMe_SSD_SED
				17:SCM_SSD
				18:SCM_SED"
			::= { hwInfoDiskEntry 5 }
		
		-- 1.3.6.1.4.1.34774.4.1.23.5.1.1.6
		hwInfoDiskCapacity OBJECT-TYPE
			SYNTAX Counter64
			MAX-ACCESS read-only
			STATUS current
			DESCRIPTION
				"Disk capacity(unit: MB)."
			::= { hwInfoDiskEntry 6 }
		
		-- 1.3.6.1.4.1.34774.4.1.23.5.1.1.7
		hwInfoDiskRole OBJECT-TYPE
			SYNTAX Unsigned32
			MAX-ACCESS read-only
			STATUS current
			DESCRIPTION
				"Logical type of a disk. Possible values are:
				1: FREE
				2: MEMBER
				3: SPARE
				4: CACHE"
			::= { hwInfoDiskEntry 7 }
		
		-- 1.3.6.1.4.1.34774.4.1.23.5.1.1.8
		hwInfoDiskSpeed OBJECT-TYPE
			SYNTAX Unsigned32
			MAX-ACCESS read-only
			STATUS current
			DESCRIPTION
				"Rotational speed of a disk(unit: rpm)."
			::= { hwInfoDiskEntry 8 }
		
		-- 1.3.6.1.4.1.34774.4.1.23.5.1.1.9
		hwInfoDiskInterfaceBandwidth OBJECT-TYPE
			SYNTAX Unsigned32
			MAX-ACCESS read-only
			STATUS current
			DESCRIPTION
				"Disk interface bandwidth(unit: Mbit/s)."
			::= { hwInfoDiskEntry 9 }
		
		-- 1.3.6.1.4.1.34774.4.1.23.5.1.1.10
		hwInfoDiskSectorSize OBJECT-TYPE
			SYNTAX Unsigned32
			MAX-ACCESS read-only
			STATUS current
			DESCRIPTION
				"Sector size of a disk (unit: B)."
			::= { hwInfoDiskEntry 10 }
		
		-- 1.3.6.1.4.1.34774.4.1.23.5.1.1.11
		hwInfoDiskTemperature OBJECT-TYPE
			SYNTAX Integer32
			MAX-ACCESS read-only
			STATUS current
			DESCRIPTION
				"Disk temperature (unit: ºC)."
			::= { hwInfoDiskEntry 11 }
		
		-- 1.3.6.1.4.1.34774.4.1.23.5.1.1.12
		hwInfoDiskModel OBJECT-TYPE
			SYNTAX OCTET STRING
			MAX-ACCESS read-only
			STATUS current
			DESCRIPTION
				"Disk model."
			::= { hwInfoDiskEntry 12 }
		
		-- 1.3.6.1.4.1.34774.4.1.23.5.1.1.13
		hwInfoDiskFirmwareVersion OBJECT-TYPE
			SYNTAX OCTET STRING
			MAX-ACCESS read-only
			STATUS current
			DESCRIPTION
				"Firmware version of a disk."
			::= { hwInfoDiskEntry 13 }
		
		-- 1.3.6.1.4.1.34774.4.1.23.5.1.1.14
		hwInfoDiskManufacturer OBJECT-TYPE
			SYNTAX OCTET STRING
			MAX-ACCESS read-only
			STATUS current
			DESCRIPTION
				"Disk manufacturer."
			::= { hwInfoDiskEntry 14 }
		
		-- 1.3.6.1.4.1.34774.4.1.23.5.1.1.15
		hwInfoDiskSerialNumber OBJECT-TYPE
			SYNTAX OCTET STRING
			MAX-ACCESS read-only
			STATUS current
			DESCRIPTION
				"Disk SN."
			::= { hwInfoDiskEntry 15 }
		
		-- 1.3.6.1.4.1.34774.4.1.23.5.1.1.16
		hwInfoDiskLightStatus OBJECT-TYPE
			SYNTAX Unsigned32
			MAX-ACCESS read-only
			STATUS current
			DESCRIPTION
				"Disk indicator status. Possible values are:
				0: OFF
				1: ON
				2: STEADY ON"
			::= { hwInfoDiskEntry 16 }
		
		-- 1.3.6.1.4.1.34774.4.1.23.5.1.1.17
		hwInfoDiskDiskDomainID OBJECT-TYPE
			SYNTAX OCTET STRING
			MAX-ACCESS read-only
			STATUS current
			DESCRIPTION
				"ID of a disk domain."
			::= { hwInfoDiskEntry 17 }
		
		-- 1.3.6.1.4.1.34774.4.1.23.5.1.1.18
		hwInfoDiskDiskDomainName OBJECT-TYPE
			SYNTAX OCTET STRING
			MAX-ACCESS read-only
			STATUS current
			DESCRIPTION
				"Name of a disk domain."
			::= { hwInfoDiskEntry 18 }
		
		-- 1.3.6.1.4.1.34774.4.1.23.5.1.1.19
		hwInfoDiskDiskDomainTierID OBJECT-TYPE
			SYNTAX OCTET STRING
			MAX-ACCESS read-only
			STATUS current
			DESCRIPTION
				"ID of a disk domain tier."
			::= { hwInfoDiskEntry 19 }
		
		-- 1.3.6.1.4.1.34774.4.1.23.5.1.1.20
		hwInfoDiskCofferDisk OBJECT-TYPE
			SYNTAX Unsigned32
			MAX-ACCESS read-only
			STATUS current
			DESCRIPTION
				"To determine whether a disk is a coffer disk. Possible values are:
				0: NO
				1: YES"
			::= { hwInfoDiskEntry 20 }
		
		-- 1.3.6.1.4.1.34774.4.1.23.5.1.1.21
		hwInfoDiskRunTime OBJECT-TYPE
			SYNTAX Unsigned32
			MAX-ACCESS read-only
			STATUS current
			DESCRIPTION
				"Disk operation period(unit: day)."
			::= { hwInfoDiskEntry 21 }
		
		-- 1.3.6.1.4.1.34774.4.1.23.5.1.1.22
		hwInfoDiskProgress OBJECT-TYPE
			SYNTAX Unsigned32
			MAX-ACCESS read-only
			STATUS current
			DESCRIPTION
				"Progress of disk reconstruction, copyback, pre-copy, or destruction(unit: %)."
			::= { hwInfoDiskEntry 22 }
		
		-- 1.3.6.1.4.1.34774.4.1.23.5.1.1.23
		hwInfoDiskBarCode OBJECT-TYPE
			SYNTAX OCTET STRING
			MAX-ACCESS read-only
			STATUS current
			DESCRIPTION
				"Disk barcode."
			::= { hwInfoDiskEntry 23 }
		
		-- 1.3.6.1.4.1.34774.4.1.23.5.1.1.24
		hwInfoDiskCapacityUsage OBJECT-TYPE
			SYNTAX Unsigned32
			MAX-ACCESS read-only
			STATUS current
			DESCRIPTION
				"Capacity usage of a disk(unit: %)."
			::= { hwInfoDiskEntry 24 }
		
		-- 1.3.6.1.4.1.34774.4.1.23.5.1.1.25
		hwInfoDiskHealthMark OBJECT-TYPE
			SYNTAX Unsigned32
			MAX-ACCESS read-only
			STATUS current
			DESCRIPTION
				"Health score of a disk. If the value is 255, indicating invalid."
			::= { hwInfoDiskEntry 25 }
            
        -- 1.3.6.1.4.1.34774.4.1.23.5.1.1.26
		hwInfoDiskElectronicLabel OBJECT-TYPE
			SYNTAX OCTET STRING
			MAX-ACCESS read-only
			STATUS current
			DESCRIPTION
				"Electronic label of a disk."
			::= { hwInfoDiskEntry 26 }
		
		-- 1.3.6.1.4.1.34774.4.1.23.5.2
		hwInfoControllerTable OBJECT-TYPE
			SYNTAX SEQUENCE OF HwInfoControllerEntry
			MAX-ACCESS not-accessible
			STATUS current
			DESCRIPTION
				"This table is used to check the controller information about a device."
			::= { hwHardwareInfo 2 }
		
		-- 1.3.6.1.4.1.34774.4.1.23.5.2.1
		hwInfoControllerEntry OBJECT-TYPE
			SYNTAX HwInfoControllerEntry
			MAX-ACCESS not-accessible
			STATUS current
			DESCRIPTION
				"A table containing the part component."
			INDEX { hwInfoControllerID }
			::= { hwInfoControllerTable 1 }
		
		HwInfoControllerEntry ::=
			SEQUENCE { 
				hwInfoControllerID
					OCTET STRING,
				hwInfoControllerHealthStatus
					Unsigned32,
				hwInfoControllerRunningStatus
					Unsigned32,
				hwInfoControllerCPU
					OCTET STRING,
				hwInfoControllerLocation
					OCTET STRING,
				hwInfoControllerRole
					Unsigned32,
				hwInfoControllerCacheCapacity
					Unsigned32,
				hwInfoControllerCPUUsage
					Unsigned32,
				hwInfoControllerMemoryUsage
					Unsigned32,
				hwInfoControllerVoltage
					Unsigned32,
				hwInfoControllerSoftwareVersion
					OCTET STRING,
				hwInfoControllerPCBVersion
					OCTET STRING,
				hwInfoControllerSESVersion
					OCTET STRING,
				hwInfoControllerBMCVersion
					OCTET STRING,
				hwInfoControllerLogicVersion
					OCTET STRING,
				hwInfoControllerBIOSVersion
					OCTET STRING,
				hwInfoControllerElectronicLabel
					OCTET STRING
			 }

		-- 1.3.6.1.4.1.34774.4.1.23.5.2.1.1
		hwInfoControllerID OBJECT-TYPE
			SYNTAX OCTET STRING
			MAX-ACCESS read-only
			STATUS current
			DESCRIPTION
				"Controller ID, table index."
			::= { hwInfoControllerEntry 1 }
		
		-- 1.3.6.1.4.1.34774.4.1.23.5.2.1.2
		hwInfoControllerHealthStatus OBJECT-TYPE
			SYNTAX Unsigned32
			MAX-ACCESS read-only
			STATUS current
			DESCRIPTION
				"Controller health status. For details, see:
				1 Normal
				2 Fault
				3 Pre-Fail
				4 Partially Broken
				5 Degraded
				6 Bad Sectors Found
				7 Bit Errors Found
				8 Consistent
				9 Inconsistent
				10 Busy
				11 No Input
				12 Low Battery
				13 Single Link Fault
				14 Invalid
				15 Write Protect
				16 single link
				17 No Redundant Link
				18 Offline"
			::= { hwInfoControllerEntry 2 }
		
		-- 1.3.6.1.4.1.34774.4.1.23.5.2.1.3
		hwInfoControllerRunningStatus OBJECT-TYPE
			SYNTAX Unsigned32
			MAX-ACCESS read-only
			STATUS current
			DESCRIPTION
				"Controller running status. For details, see:
				1: Normal
				2: Running
				3: Not running
				4: Not existed
				5: Sleep in high temperature
				6: Starting
				7: Power failure rotection
				8: Spin down
				9: Started
				10: Link Up
				11: Link Down
				12: Powering on
				13: Powered off
				14: Pre-copy
				15: Copyback
				16: Reconstruction
				17: Expansion
				18: Unformatted
				19: Formatting
				20: Unmapped
				21: Initial synchronizing
				22: Consistent
				23: Synchronizing
				24: Synchronized
				25: Unsynchronized
				26: Split
				27: Online
				28: Offline
				29: Locked
				30: Enabled
				31: Disabled
				32: Balancing
				33: To be recovered
				34: Interrupted
				35: Invalid
				36: Not start
				37: Queuing
				38: Stopped
				39: Copying
				40: Completed
				41: Paused
				42: Reverse synchronizing
				43: Activated
				44: Restore
				45: Inactive
				46: Idle
				47: Powering off
				48: Charging
				49: Charging completed
				50: Discharging
				51: Upgrading
				52: Power Lost
				53: Initializing
				54: Apply change
				55: Online disable
				56: Offline disable
				57: Online frozen
				58: Offline frozen
				59: Closed
				60: Removing
				61: In service
				62: Out of service
				63: Running normal
				64: Running fail
				65: Running success
				66: Running success
				67: Running failed
				68: Waiting
				69: Canceling
				70: Canceled
				71: About to synchronize
				72: Synchronizing data
				73: Failed to synchronize
				74: Fault
				75: Migrating
				76: Migrated
				77: Activating
				78: Deactivating
				79: Start failed
				80: Stop failed
				81: Decommissioning
				82: Decommissioned
				83: Recommissioning
				84: Replacing node
				85: Scheduling
				86: Pausing
				87: Suspending
				88: Suspended
				89: Overload
				90: To be switch
				91: Switching
				92: To be cleanup
				93: Forced start
				94: Error
				95: Job completed
				96: Partition Migrating
				97: Mount
				98: Umount
				99: INSTALLING
				100: To Be Synchronized
				101: Connecting
				102: Service Switching
				103: Power-on failed
				104: REPAIRING
				105: abnormal
				106: Deleting
				107: Modifying
				108: Running(clearing data)
				109: Running(synchronizing data)
				110: Standby
				111: STOPPING
				112: RESTORE FAULT
				113: Cut Over
				114: Erasing
				115: Verifying
				119: Creating"
			::= { hwInfoControllerEntry 3 }
		
		-- 1.3.6.1.4.1.34774.4.1.23.5.2.1.4
		hwInfoControllerCPU OBJECT-TYPE
			SYNTAX OCTET STRING
			MAX-ACCESS read-only
			STATUS current
			DESCRIPTION
				"Controller CPU."
			::= { hwInfoControllerEntry 4 }
		
		-- 1.3.6.1.4.1.34774.4.1.23.5.2.1.5
		hwInfoControllerLocation OBJECT-TYPE
			SYNTAX OCTET STRING
			MAX-ACCESS read-only
			STATUS current
			DESCRIPTION
				"Controller location."
			::= { hwInfoControllerEntry 5 }
		
		-- 1.3.6.1.4.1.34774.4.1.23.5.2.1.6
		hwInfoControllerRole OBJECT-TYPE
			SYNTAX Unsigned32
			MAX-ACCESS read-only
			STATUS current
			DESCRIPTION
				"Controller role. Possible values are:
				0: Normal
				1: Master
				2: Slave"
			::= { hwInfoControllerEntry 6 }
		
		-- 1.3.6.1.4.1.34774.4.1.23.5.2.1.7
		hwInfoControllerCacheCapacity OBJECT-TYPE
			SYNTAX Unsigned32
			MAX-ACCESS read-only
			STATUS current
			DESCRIPTION
				"Cache capacity of a controller (unit: MB)."
			::= { hwInfoControllerEntry 7 }
		
		-- 1.3.6.1.4.1.34774.4.1.23.5.2.1.8
		hwInfoControllerCPUUsage OBJECT-TYPE
			SYNTAX Unsigned32
			MAX-ACCESS read-only
			STATUS current
			DESCRIPTION
				"CPU usage of a controller (unit: %)."
			::= { hwInfoControllerEntry 8 }
		
		-- 1.3.6.1.4.1.34774.4.1.23.5.2.1.9
		hwInfoControllerMemoryUsage OBJECT-TYPE
			SYNTAX Unsigned32
			MAX-ACCESS read-only
			STATUS current
			DESCRIPTION
				"Memory usage of the operating system in the controller (unit: %)."
			::= { hwInfoControllerEntry 9 }
		
		-- 1.3.6.1.4.1.34774.4.1.23.5.2.1.10
		hwInfoControllerVoltage OBJECT-TYPE
			SYNTAX Unsigned32
			MAX-ACCESS read-only
			STATUS current
			DESCRIPTION
				"Power voltage of a controller (unit: 0.1 V)."
			::= { hwInfoControllerEntry 10 }
		
		-- 1.3.6.1.4.1.34774.4.1.23.5.2.1.11
		hwInfoControllerSoftwareVersion OBJECT-TYPE
			SYNTAX OCTET STRING
			MAX-ACCESS read-only
			STATUS current
			DESCRIPTION
				"Software version of a controller."
			::= { hwInfoControllerEntry 11 }
		
		-- 1.3.6.1.4.1.34774.4.1.23.5.2.1.12
		hwInfoControllerPCBVersion OBJECT-TYPE
			SYNTAX OCTET STRING
			MAX-ACCESS read-only
			STATUS current
			DESCRIPTION
				"PCB version of a controller."
			::= { hwInfoControllerEntry 12 }
		
		-- 1.3.6.1.4.1.34774.4.1.23.5.2.1.13
		hwInfoControllerSESVersion OBJECT-TYPE
			SYNTAX OCTET STRING
			MAX-ACCESS read-only
			STATUS current
			DESCRIPTION
				"SES version of a controller."
			::= { hwInfoControllerEntry 13 }
		
		-- 1.3.6.1.4.1.34774.4.1.23.5.2.1.14
		hwInfoControllerBMCVersion OBJECT-TYPE
			SYNTAX OCTET STRING
			MAX-ACCESS read-only
			STATUS current
			DESCRIPTION
				"BMC version of a controller. When the value is empty or "--", indicates unknown or invalid."
			::= { hwInfoControllerEntry 14 }
		
		-- 1.3.6.1.4.1.34774.4.1.23.5.2.1.15
		hwInfoControllerLogicVersion OBJECT-TYPE
			SYNTAX OCTET STRING
			MAX-ACCESS read-only
			STATUS current
			DESCRIPTION
				"Logical version of a controller."
			::= { hwInfoControllerEntry 15 }
		
		-- 1.3.6.1.4.1.34774.4.1.23.5.2.1.16
		hwInfoControllerBIOSVersion OBJECT-TYPE
			SYNTAX OCTET STRING
			MAX-ACCESS read-only
			STATUS current
			DESCRIPTION
				"BIOS version of a controller."
			::= { hwInfoControllerEntry 16 }
		
		-- 1.3.6.1.4.1.34774.4.1.23.5.2.1.17
		hwInfoControllerElectronicLabel OBJECT-TYPE
			SYNTAX OCTET STRING
			MAX-ACCESS read-only
			STATUS current
			DESCRIPTION
				"Electronic label of a controller."
			::= { hwInfoControllerEntry 17 }
		
		-- 1.3.6.1.4.1.34774.4.1.23.5.3
		hwInfoPowerTable OBJECT-TYPE
			SYNTAX SEQUENCE OF HwInfoPowerEntry
			MAX-ACCESS not-accessible
			STATUS current
			DESCRIPTION
				"This table is used to check the power supply information about a device."
			::= { hwHardwareInfo 3 }
		
		-- 1.3.6.1.4.1.34774.4.1.23.5.3.1
		hwInfoPowerEntry OBJECT-TYPE
			SYNTAX HwInfoPowerEntry
			MAX-ACCESS not-accessible
			STATUS current
			DESCRIPTION
				"A table containing the part component."
			INDEX { hwInfoPowerID }
			::= { hwInfoPowerTable 1 }
		
		HwInfoPowerEntry ::=
			SEQUENCE { 
				hwInfoPowerID
					OCTET STRING,
				hwInfoPowerLocation
					OCTET STRING,
				hwInfoPowerHealthStatus
					Unsigned32,
				hwInfoPowerRunningStatus
					Unsigned32,
				hwInfoPowerType
					Unsigned32,
				hwInfoPowerManufacturer
					OCTET STRING,
				hwInfoPowerModle
					OCTET STRING,
				hwInfoPowerVersion
					OCTET STRING,
				hwInfoPowerProduceDate
					OCTET STRING,
				hwInfoPowerSerialNumber
					OCTET STRING
			 }

		-- 1.3.6.1.4.1.34774.4.1.23.5.3.1.1
		hwInfoPowerID OBJECT-TYPE
			SYNTAX OCTET STRING
			MAX-ACCESS read-only
			STATUS current
			DESCRIPTION
				"ID of a power supply, table index."
			::= { hwInfoPowerEntry 1 }
		
		-- 1.3.6.1.4.1.34774.4.1.23.5.3.1.2
		hwInfoPowerLocation OBJECT-TYPE
			SYNTAX OCTET STRING
			MAX-ACCESS read-only
			STATUS current
			DESCRIPTION
				"Location of a power supply."
			::= { hwInfoPowerEntry 2 }
		
		-- 1.3.6.1.4.1.34774.4.1.23.5.3.1.3
		hwInfoPowerHealthStatus OBJECT-TYPE
			SYNTAX Unsigned32
			MAX-ACCESS read-only
			STATUS current
			DESCRIPTION
				"Health status of a power supply. For details, see:
				1 Normal
				2 Fault
				3 Pre-Fail
				4 Partially Broken
				5 Degraded
				6 Bad Sectors Found
				7 Bit Errors Found
				8 Consistent
				9 Inconsistent
				10 Busy
				11 No Input
				12 Low Battery
				13 Single Link Fault
				14 Invalid
				15 Write Protect
				16 single link
				17 No Redundant Link
				18 Offline"
			::= { hwInfoPowerEntry 3 }
		
		-- 1.3.6.1.4.1.34774.4.1.23.5.3.1.4
		hwInfoPowerRunningStatus OBJECT-TYPE
			SYNTAX Unsigned32
			MAX-ACCESS read-only
			STATUS current
			DESCRIPTION
				"Operating status of a power supply. For details, see:
				1: Normal
				2: Running
				3: Not running
				4: Not existed
				5: Sleep in high temperature
				6: Starting
				7: Power failure rotection
				8: Spin down
				9: Started
				10: Link Up
				11: Link Down
				12: Powering on
				13: Powered off
				14: Pre-copy
				15: Copyback
				16: Reconstruction
				17: Expansion
				18: Unformatted
				19: Formatting
				20: Unmapped
				21: Initial synchronizing
				22: Consistent
				23: Synchronizing
				24: Synchronized
				25: Unsynchronized
				26: Split
				27: Online
				28: Offline
				29: Locked
				30: Enabled
				31: Disabled
				32: Balancing
				33: To be recovered
				34: Interrupted
				35: Invalid
				36: Not start
				37: Queuing
				38: Stopped
				39: Copying
				40: Completed
				41: Paused
				42: Reverse synchronizing
				43: Activated
				44: Restore
				45: Inactive
				46: Idle
				47: Powering off
				48: Charging
				49: Charging completed
				50: Discharging
				51: Upgrading
				52: Power Lost
				53: Initializing
				54: Apply change
				55: Online disable
				56: Offline disable
				57: Online frozen
				58: Offline frozen
				59: Closed
				60: Removing
				61: In service
				62: Out of service
				63: Running normal
				64: Running fail
				65: Running success
				66: Running success
				67: Running failed
				68: Waiting
				69: Canceling
				70: Canceled
				71: About to synchronize
				72: Synchronizing data
				73: Failed to synchronize
				74: Fault
				75: Migrating
				76: Migrated
				77: Activating
				78: Deactivating
				79: Start failed
				80: Stop failed
				81: Decommissioning
				82: Decommissioned
				83: Recommissioning
				84: Replacing node
				85: Scheduling
				86: Pausing
				87: Suspending
				88: Suspended
				89: Overload
				90: To be switch
				91: Switching
				92: To be cleanup
				93: Forced start
				94: Error
				95: Job completed
				96: Partition Migrating
				97: Mount
				98: Umount
				99: INSTALLING
				100: To Be Synchronized
				101: Connecting
				102: Service Switching
				103: Power-on failed
				104: REPAIRING
				105: abnormal
				106: Deleting
				107: Modifying
				108: Running(clearing data)
				109: Running(synchronizing data)
				110: Standby
				111: STOPPING
				112: RESTORE FAULT
				113: Cut Over
				114: Erasing
				115: Verifying
				119: Creating"
			::= { hwInfoPowerEntry 4 }
		
		-- 1.3.6.1.4.1.34774.4.1.23.5.3.1.5
		hwInfoPowerType OBJECT-TYPE
			SYNTAX Unsigned32
			MAX-ACCESS read-only
			STATUS current
			DESCRIPTION
				"Type of a power supply. Possible values are:
				0: DC
				1: AC
				2: HV
				255:Unknown"
			::= { hwInfoPowerEntry 5 }
		
		-- 1.3.6.1.4.1.34774.4.1.23.5.3.1.6
		hwInfoPowerManufacturer OBJECT-TYPE
			SYNTAX OCTET STRING
			MAX-ACCESS read-only
			STATUS current
			DESCRIPTION
				"Manufacturer of a power supply."
			::= { hwInfoPowerEntry 6 }
		
		-- 1.3.6.1.4.1.34774.4.1.23.5.3.1.7
		hwInfoPowerModle OBJECT-TYPE
			SYNTAX OCTET STRING
			MAX-ACCESS read-only
			STATUS current
			DESCRIPTION
				"Model of a power supply."
			::= { hwInfoPowerEntry 7 }
		
		-- 1.3.6.1.4.1.34774.4.1.23.5.3.1.8
		hwInfoPowerVersion OBJECT-TYPE
			SYNTAX OCTET STRING
			MAX-ACCESS read-only
			STATUS current
			DESCRIPTION
				"Version of a power supply."
			::= { hwInfoPowerEntry 8 }
		
		-- 1.3.6.1.4.1.34774.4.1.23.5.3.1.9
		hwInfoPowerProduceDate OBJECT-TYPE
			SYNTAX OCTET STRING
			MAX-ACCESS read-only
			STATUS current
			DESCRIPTION
				"Production date of a power supply."
			::= { hwInfoPowerEntry 9 }
		
		-- 1.3.6.1.4.1.34774.4.1.23.5.3.1.10
		hwInfoPowerSerialNumber OBJECT-TYPE
			SYNTAX OCTET STRING
			MAX-ACCESS read-only
			STATUS current
			DESCRIPTION
				"SN of a power supply."
			::= { hwInfoPowerEntry 10 }
		
		-- 1.3.6.1.4.1.34774.4.1.23.5.4
		hwInfoFanTable OBJECT-TYPE
			SYNTAX SEQUENCE OF HwInfoFanEntry
			MAX-ACCESS not-accessible
			STATUS current
			DESCRIPTION
				"This table is used to check the fan information about a device."
			::= { hwHardwareInfo 4 }
		
		-- 1.3.6.1.4.1.34774.4.1.23.5.4.1
		hwInfoFanEntry OBJECT-TYPE
			SYNTAX HwInfoFanEntry
			MAX-ACCESS not-accessible
			STATUS current
			DESCRIPTION
				"A table containing the part component."
			INDEX { hwInfoFanID }
			::= { hwInfoFanTable 1 }
		
		HwInfoFanEntry ::=
			SEQUENCE { 
				hwInfoFanID
					OCTET STRING,
				hwInfoFanLocation
					OCTET STRING,
				hwInfoFanHealthStatus
					Unsigned32,
				hwInfoFanRunningStatus
					Unsigned32,
				hwInfoFanRunningLevel
					Unsigned32,
				hwInfoFanElectronicLabel
					OCTET STRING
			 }

		-- 1.3.6.1.4.1.34774.4.1.23.5.4.1.1
		hwInfoFanID OBJECT-TYPE
			SYNTAX OCTET STRING
			MAX-ACCESS read-only
			STATUS current
			DESCRIPTION
				"Fan ID, table index."
			::= { hwInfoFanEntry 1 }
		
		-- 1.3.6.1.4.1.34774.4.1.23.5.4.1.2
		hwInfoFanLocation OBJECT-TYPE
			SYNTAX OCTET STRING
			MAX-ACCESS read-only
			STATUS current
			DESCRIPTION
				"Fan Location."
			::= { hwInfoFanEntry 2 }
		
		-- 1.3.6.1.4.1.34774.4.1.23.5.4.1.3
		hwInfoFanHealthStatus OBJECT-TYPE
			SYNTAX Unsigned32
			MAX-ACCESS read-only
			STATUS current
			DESCRIPTION
				"Health status of a fan. For details, see:
				1 Normal
				2 Fault
				3 Pre-Fail
				4 Partially Broken
				5 Degraded
				6 Bad Sectors Found
				7 Bit Errors Found
				8 Consistent
				9 Inconsistent
				10 Busy
				11 No Input
				12 Low Battery
				13 Single Link Fault
				14 Invalid
				15 Write Protect
				16 single link
				17 No Redundant Link
				18 Offline"
			::= { hwInfoFanEntry 3 }
		
		-- 1.3.6.1.4.1.34774.4.1.23.5.4.1.4
		hwInfoFanRunningStatus OBJECT-TYPE
			SYNTAX Unsigned32
			MAX-ACCESS read-only
			STATUS current
			DESCRIPTION
				"Operating status of a fan. For details, see:
				1: Normal
				2: Running
				3: Not running
				4: Not existed
				5: Sleep in high temperature
				6: Starting
				7: Power failure rotection
				8: Spin down
				9: Started
				10: Link Up
				11: Link Down
				12: Powering on
				13: Powered off
				14: Pre-copy
				15: Copyback
				16: Reconstruction
				17: Expansion
				18: Unformatted
				19: Formatting
				20: Unmapped
				21: Initial synchronizing
				22: Consistent
				23: Synchronizing
				24: Synchronized
				25: Unsynchronized
				26: Split
				27: Online
				28: Offline
				29: Locked
				30: Enabled
				31: Disabled
				32: Balancing
				33: To be recovered
				34: Interrupted
				35: Invalid
				36: Not start
				37: Queuing
				38: Stopped
				39: Copying
				40: Completed
				41: Paused
				42: Reverse synchronizing
				43: Activated
				44: Restore
				45: Inactive
				46: Idle
				47: Powering off
				48: Charging
				49: Charging completed
				50: Discharging
				51: Upgrading
				52: Power Lost
				53: Initializing
				54: Apply change
				55: Online disable
				56: Offline disable
				57: Online frozen
				58: Offline frozen
				59: Closed
				60: Removing
				61: In service
				62: Out of service
				63: Running normal
				64: Running fail
				65: Running success
				66: Running success
				67: Running failed
				68: Waiting
				69: Canceling
				70: Canceled
				71: About to synchronize
				72: Synchronizing data
				73: Failed to synchronize
				74: Fault
				75: Migrating
				76: Migrated
				77: Activating
				78: Deactivating
				79: Start failed
				80: Stop failed
				81: Decommissioning
				82: Decommissioned
				83: Recommissioning
				84: Replacing node
				85: Scheduling
				86: Pausing
				87: Suspending
				88: Suspended
				89: Overload
				90: To be switch
				91: Switching
				92: To be cleanup
				93: Forced start
				94: Error
				95: Job completed
				96: Partition Migrating
				97: Mount
				98: Umount
				99: INSTALLING
				100: To Be Synchronized
				101: Connecting
				102: Service Switching
				103: Power-on failed
				104: REPAIRING
				105: abnormal
				106: Deleting
				107: Modifying
				108: Running(clearing data)
				109: Running(synchronizing data)
				110: Standby
				111: STOPPING
				112: RESTORE FAULT
				113: Cut Over
				114: Erasing
				115: Verifying
				119: Creating"
			::= { hwInfoFanEntry 4 }
		
		-- 1.3.6.1.4.1.34774.4.1.23.5.4.1.5
		hwInfoFanRunningLevel OBJECT-TYPE
			SYNTAX Unsigned32
			MAX-ACCESS read-only
			STATUS current
			DESCRIPTION
				"Operating level of a fan. Possible values are:
				0: Low
				1: Normal
				2: High"
			::= { hwInfoFanEntry 5 }
		
		-- 1.3.6.1.4.1.34774.4.1.23.5.4.1.6
		hwInfoFanElectronicLabel OBJECT-TYPE
			SYNTAX OCTET STRING
			MAX-ACCESS read-only
			STATUS current
			DESCRIPTION
				"Electronic label of a fan."
			::= { hwInfoFanEntry 6 }
		
		-- 1.3.6.1.4.1.34774.4.1.23.5.5
		hwInfoBBUTable OBJECT-TYPE
			SYNTAX SEQUENCE OF HwInfoBBUEntry
			MAX-ACCESS not-accessible
			STATUS current
			DESCRIPTION
				"This table is used to check the BBU information about a device."
			::= { hwHardwareInfo 5 }
		
		-- 1.3.6.1.4.1.34774.4.1.23.5.5.1
		hwInfoBBUEntry OBJECT-TYPE
			SYNTAX HwInfoBBUEntry
			MAX-ACCESS not-accessible
			STATUS current
			DESCRIPTION
				"A table containing the part component."
			INDEX { hwInfoBBUID }
			::= { hwInfoBBUTable 1 }
		
		HwInfoBBUEntry ::=
			SEQUENCE { 
				hwInfoBBUID
					OCTET STRING,
				hwInfoBBULocation
					OCTET STRING,
				hwInfoBBUHealthStatus
					Unsigned32,
				hwInfoBBURunningStatus
					Unsigned32,
				hwInfoBBUType
					Unsigned32,
				hwInfoBBUCurrentVoltage
					Unsigned32,
				hwInfoBBUNumberOfDischarges
					Unsigned32,
				hwInfoBBUFirmwareVersion
					OCTET STRING,
				hwInfoBBUDeliveredOn
					OCTET STRING,
				hwInfoBBUOwningController
					OCTET STRING,
				hwInfoBBUElectronicLabel
					OCTET STRING
			 }

		-- 1.3.6.1.4.1.34774.4.1.23.5.5.1.1
		hwInfoBBUID OBJECT-TYPE
			SYNTAX OCTET STRING
			MAX-ACCESS read-only
			STATUS current
			DESCRIPTION
				"BBU ID, table index."
			::= { hwInfoBBUEntry 1 }
		
		-- 1.3.6.1.4.1.34774.4.1.23.5.5.1.2
		hwInfoBBULocation OBJECT-TYPE
			SYNTAX OCTET STRING
			MAX-ACCESS read-only
			STATUS current
			DESCRIPTION
				"BBU Location."
			::= { hwInfoBBUEntry 2 }
		
		-- 1.3.6.1.4.1.34774.4.1.23.5.5.1.3
		hwInfoBBUHealthStatus OBJECT-TYPE
			SYNTAX Unsigned32
			MAX-ACCESS read-only
			STATUS current
			DESCRIPTION
				"Health status of a BBU. For details, see:
				1 Normal
				2 Fault
				3 Pre-Fail
				4 Partially Broken
				5 Degraded
				6 Bad Sectors Found
				7 Bit Errors Found
				8 Consistent
				9 Inconsistent
				10 Busy
				11 No Input
				12 Low Battery
				13 Single Link Fault
				14 Invalid
				15 Write Protect
				16 single link
				17 No Redundant Link
				18 Offline"
			::= { hwInfoBBUEntry 3 }
		
		-- 1.3.6.1.4.1.34774.4.1.23.5.5.1.4
		hwInfoBBURunningStatus OBJECT-TYPE
			SYNTAX Unsigned32
			MAX-ACCESS read-only
			STATUS current
			DESCRIPTION
				"Running status of a BBU. For details, see:
				1: Normal
				2: Running
				3: Not running
				4: Not existed
				5: Sleep in high temperature
				6: Starting
				7: Power failure rotection
				8: Spin down
				9: Started
				10: Link Up
				11: Link Down
				12: Powering on
				13: Powered off
				14: Pre-copy
				15: Copyback
				16: Reconstruction
				17: Expansion
				18: Unformatted
				19: Formatting
				20: Unmapped
				21: Initial synchronizing
				22: Consistent
				23: Synchronizing
				24: Synchronized
				25: Unsynchronized
				26: Split
				27: Online
				28: Offline
				29: Locked
				30: Enabled
				31: Disabled
				32: Balancing
				33: To be recovered
				34: Interrupted
				35: Invalid
				36: Not start
				37: Queuing
				38: Stopped
				39: Copying
				40: Completed
				41: Paused
				42: Reverse synchronizing
				43: Activated
				44: Restore
				45: Inactive
				46: Idle
				47: Powering off
				48: Charging
				49: Charging completed
				50: Discharging
				51: Upgrading
				52: Power Lost
				53: Initializing
				54: Apply change
				55: Online disable
				56: Offline disable
				57: Online frozen
				58: Offline frozen
				59: Closed
				60: Removing
				61: In service
				62: Out of service
				63: Running normal
				64: Running fail
				65: Running success
				66: Running success
				67: Running failed
				68: Waiting
				69: Canceling
				70: Canceled
				71: About to synchronize
				72: Synchronizing data
				73: Failed to synchronize
				74: Fault
				75: Migrating
				76: Migrated
				77: Activating
				78: Deactivating
				79: Start failed
				80: Stop failed
				81: Decommissioning
				82: Decommissioned
				83: Recommissioning
				84: Replacing node
				85: Scheduling
				86: Pausing
				87: Suspending
				88: Suspended
				89: Overload
				90: To be switch
				91: Switching
				92: To be cleanup
				93: Forced start
				94: Error
				95: Job completed
				96: Partition Migrating
				97: Mount
				98: Umount
				99: INSTALLING
				100: To Be Synchronized
				101: Connecting
				102: Service Switching
				103: Power-on failed
				104: REPAIRING
				105: abnormal
				106: Deleting
				107: Modifying
				108: Running(clearing data)
				109: Running(synchronizing data)
				110: Standby
				111: STOPPING
				112: RESTORE FAULT
				113: Cut Over
				114: Erasing
				115: Verifying
				119: Creating"
			::= { hwInfoBBUEntry 4 }
		
		-- 1.3.6.1.4.1.34774.4.1.23.5.5.1.5
		hwInfoBBUType OBJECT-TYPE
			SYNTAX Unsigned32
			MAX-ACCESS read-only
			STATUS current
			DESCRIPTION
				"Type of a BBU. Possible values are:
				0: BBU"
			::= { hwInfoBBUEntry 5 }
		
		-- 1.3.6.1.4.1.34774.4.1.23.5.5.1.6
		hwInfoBBUCurrentVoltage OBJECT-TYPE
			SYNTAX Unsigned32
			MAX-ACCESS read-only
			STATUS current
			DESCRIPTION
				"Current voltage of a BBU (unit: 0.1 V)."
			::= { hwInfoBBUEntry 6 }
		
		-- 1.3.6.1.4.1.34774.4.1.23.5.5.1.7
		hwInfoBBUNumberOfDischarges OBJECT-TYPE
			SYNTAX Unsigned32
			MAX-ACCESS read-only
			STATUS current
			DESCRIPTION
				"Discharge times of a BBU(unit: times)."
			::= { hwInfoBBUEntry 7 }
		
		-- 1.3.6.1.4.1.34774.4.1.23.5.5.1.8
		hwInfoBBUFirmwareVersion OBJECT-TYPE
			SYNTAX OCTET STRING
			MAX-ACCESS read-only
			STATUS current
			DESCRIPTION
				"Firmware version of a BBU."
			::= { hwInfoBBUEntry 8 }
		
		-- 1.3.6.1.4.1.34774.4.1.23.5.5.1.9
		hwInfoBBUDeliveredOn OBJECT-TYPE
			SYNTAX OCTET STRING
			MAX-ACCESS read-only
			STATUS current
			DESCRIPTION
				"Shipping date of a BBU."
			::= { hwInfoBBUEntry 9 }
		
		-- 1.3.6.1.4.1.34774.4.1.23.5.5.1.10
		hwInfoBBUOwningController OBJECT-TYPE
			SYNTAX OCTET STRING
			MAX-ACCESS read-only
			STATUS current
			DESCRIPTION
				"Owning controller of a BBU."
			::= { hwInfoBBUEntry 10 }
		
		-- 1.3.6.1.4.1.34774.4.1.23.5.5.1.11
		hwInfoBBUElectronicLabel OBJECT-TYPE
			SYNTAX OCTET STRING
			MAX-ACCESS read-only
			STATUS current
			DESCRIPTION
				"Electronic label of a BBU."
			::= { hwInfoBBUEntry 11 }
		
		-- 1.3.6.1.4.1.34774.4.1.23.5.6
		hwInfoEnclosureTable OBJECT-TYPE
			SYNTAX SEQUENCE OF HwInfoEnclosureEntry
			MAX-ACCESS not-accessible
			STATUS current
			DESCRIPTION
				"This table is used to check the enclosure information about a device."
			::= { hwHardwareInfo 6 }
		
		-- 1.3.6.1.4.1.34774.4.1.23.5.6.1
		hwInfoEnclosureEntry OBJECT-TYPE
			SYNTAX HwInfoEnclosureEntry
			MAX-ACCESS not-accessible
			STATUS current
			DESCRIPTION
				"A table containing the part component."
			INDEX { hwInfoEnclosureID }
			::= { hwInfoEnclosureTable 1 }
		
		HwInfoEnclosureEntry ::=
			SEQUENCE { 
				hwInfoEnclosureID
					OCTET STRING,
				hwInfoEnclosureName
					OCTET STRING,
				hwInfoEnclosureLogicType
					Unsigned32,
				hwInfoEnclosureHealthStatus
					Unsigned32,
				hwInfoEnclosureRunningStatus
					Unsigned32,
				hwInfoEnclosureLocation
					OCTET STRING,
				hwInfoEnclosureType
					Unsigned32,
				hwInfoEnclosureTemperature
					Integer32,
				hwInfoEnclosureSN
					OCTET STRING,
				hwInfoEnclosureMAC
					OCTET STRING,
				hwInfoEnclosureHeight
					Unsigned32,
				hwInfoEnclosureExpansionDepth
					Unsigned32,
				hwInfoEnclosureElectronicLabel
					OCTET STRING
			 }

		-- 1.3.6.1.4.1.34774.4.1.23.5.6.1.1
		hwInfoEnclosureID OBJECT-TYPE
			SYNTAX OCTET STRING
			MAX-ACCESS read-only
			STATUS current
			DESCRIPTION
				"Enclosure ID, table index."
			::= { hwInfoEnclosureEntry 1 }
		
		-- 1.3.6.1.4.1.34774.4.1.23.5.6.1.2
		hwInfoEnclosureName OBJECT-TYPE
			SYNTAX OCTET STRING
			MAX-ACCESS read-only
			STATUS current
			DESCRIPTION
				"Enclosure name."
			::= { hwInfoEnclosureEntry 2 }
		
		-- 1.3.6.1.4.1.34774.4.1.23.5.6.1.3
		hwInfoEnclosureLogicType OBJECT-TYPE
			SYNTAX Unsigned32
			MAX-ACCESS read-only
			STATUS current
			DESCRIPTION
				"Logical type of an enclosure. Possible values are:
				0: EXP
				1: CTRL
				2: DSW
				3: MSW
				4: SVP"
			::= { hwInfoEnclosureEntry 3 }
		
		-- 1.3.6.1.4.1.34774.4.1.23.5.6.1.4
		hwInfoEnclosureHealthStatus OBJECT-TYPE
			SYNTAX Unsigned32
			MAX-ACCESS read-only
			STATUS current
			DESCRIPTION
				"Health status of an enclosure. For details, see:
				1 Normal
				2 Fault
				3 Pre-Fail
				4 Partially Broken
				5 Degraded
				6 Bad Sectors Found
				7 Bit Errors Found
				8 Consistent
				9 Inconsistent
				10 Busy
				11 No Input
				12 Low Battery
				13 Single Link Fault
				14 Invalid
				15 Write Protect
				16 single link
				17 No Redundant Link
				18 Offline"
			::= { hwInfoEnclosureEntry 4 }
		
		-- 1.3.6.1.4.1.34774.4.1.23.5.6.1.5
		hwInfoEnclosureRunningStatus OBJECT-TYPE
			SYNTAX Unsigned32
			MAX-ACCESS read-only
			STATUS current
			DESCRIPTION
				"Operating status of an enclosure. For details, see:
				1: Normal
				2: Running
				3: Not running
				4: Not existed
				5: Sleep in high temperature
				6: Starting
				7: Power failure rotection
				8: Spin down
				9: Started
				10: Link Up
				11: Link Down
				12: Powering on
				13: Powered off
				14: Pre-copy
				15: Copyback
				16: Reconstruction
				17: Expansion
				18: Unformatted
				19: Formatting
				20: Unmapped
				21: Initial synchronizing
				22: Consistent
				23: Synchronizing
				24: Synchronized
				25: Unsynchronized
				26: Split
				27: Online
				28: Offline
				29: Locked
				30: Enabled
				31: Disabled
				32: Balancing
				33: To be recovered
				34: Interrupted
				35: Invalid
				36: Not start
				37: Queuing
				38: Stopped
				39: Copying
				40: Completed
				41: Paused
				42: Reverse synchronizing
				43: Activated
				44: Restore
				45: Inactive
				46: Idle
				47: Powering off
				48: Charging
				49: Charging completed
				50: Discharging
				51: Upgrading
				52: Power Lost
				53: Initializing
				54: Apply change
				55: Online disable
				56: Offline disable
				57: Online frozen
				58: Offline frozen
				59: Closed
				60: Removing
				61: In service
				62: Out of service
				63: Running normal
				64: Running fail
				65: Running success
				66: Running success
				67: Running failed
				68: Waiting
				69: Canceling
				70: Canceled
				71: About to synchronize
				72: Synchronizing data
				73: Failed to synchronize
				74: Fault
				75: Migrating
				76: Migrated
				77: Activating
				78: Deactivating
				79: Start failed
				80: Stop failed
				81: Decommissioning
				82: Decommissioned
				83: Recommissioning
				84: Replacing node
				85: Scheduling
				86: Pausing
				87: Suspending
				88: Suspended
				89: Overload
				90: To be switch
				91: Switching
				92: To be cleanup
				93: Forced start
				94: Error
				95: Job completed
				96: Partition Migrating
				97: Mount
				98: Umount
				99: INSTALLING
				100: To Be Synchronized
				101: Connecting
				102: Service Switching
				103: Power-on failed
				104: REPAIRING
				105: abnormal
				106: Deleting
				107: Modifying
				108: Running(clearing data)
				109: Running(synchronizing data)
				110: Standby
				111: STOPPING
				112: RESTORE FAULT
				113: Cut Over
				114: Erasing
				115: Verifying
				119: Creating"
			::= { hwInfoEnclosureEntry 5 }
		
		-- 1.3.6.1.4.1.34774.4.1.23.5.6.1.6
		hwInfoEnclosureLocation OBJECT-TYPE
			SYNTAX OCTET STRING
			MAX-ACCESS read-only
			STATUS current
			DESCRIPTION
				"Enclosure location."
			::= { hwInfoEnclosureEntry 6 }
		
		-- 1.3.6.1.4.1.34774.4.1.23.5.6.1.7
		hwInfoEnclosureType OBJECT-TYPE
			SYNTAX Unsigned32
			MAX-ACCESS read-only
			STATUS current
			DESCRIPTION
				"Enclosure type. Possible values are:
				0:BMC Controller
				1:2 U 2-controller 12-slot 3.5-inch 6 Gbit/s SAS controller enclosure
				2:2 U 2-controller 24-slot 2.5-inch 6 Gbit/s SAS controller enclosure
				16:2 U 12-slot 3.5-inch 6 Gbit/s SAS disk enclosure
				17:2 U 24-slot 2.5-inch 6 Gbit/s SAS disk enclosure
				18:4 U 24-slot 3.5-inch 6 Gbit/s SAS disk enclosure
				19:4 U 24 Slot 3.5 FC Disks Enclosure
				20:1 U PCIE Switch Enclosure
				21:4 U 75-slot 3.5-inch 6 Gbit/s SAS disk enclosure
				22:Service Processor Enclosure
				23:2 U 2-controller 12-slot 3.5-inch 6 Gbit/s SAS controller enclosure
				24:2 U 25-slot 2.5-inch 6 Gbit/s SAS disk enclosure
				25:4 U 24-slot 3.5-inch 6 Gbit/s SAS disk enclosure
				26:2 U 2-controller 25-slot 2.5-inch 6 Gbit/s SAS controller enclosure
				37:2 U 2-controller 12-slot 3.5-inch 6 Gbit/s SAS controller enclosure
				38:2 U 2-controller 25-slot 2.5-inch 6 Gbit/s SAS controller enclosure
				39:4 U 75-slot 3.5-inch 12 Gbit/s SAS disk enclosure
				40:2 U 2-controller 25-slot 2.5-inch 12 Gbit/s SAS controller enclosure
				65:2 U 25-slot 2.5-inch 12 Gbit/s SAS disk enclosure
				66:4 U 24-slot 3.5-inch 12 Gbit/s SAS disk enclosure
				67:2 U 25-slot 2.5-inch SAS disk enclosure
				69:4 U 24-slot 3.5-inch SAS disk enclosure
				96:3 U 2-controller controller enclosure
				97:6 U 4-controller controller enclosure
				98:2 U 25 Slot 2.5 SSD Disks Enclosure
				99:2 U 25-slot 2.5-inch active NVMe controller enclosure
				101:2 U 25-slot 2.5-inch SSD NVMe disk enclosure
				112:4 U 4-controller controller enclosure
				113:2 U 2-controller 25-slot 2.5-inch SAS controller enclosure
				114:2 U 2-controller 12-slot 3.5-inch SAS controller enclosure
				115:2 U 2-controller 36-slot NVMe controller enclosure
				116:2 U 2-controller 25-slot 2.5-inch SAS controller enclosure
				117:2 U 2-controller 12-slot 3.5-inch SAS controller enclosure
				118:2 U 25-slot 2.5-inch smart SAS disk enclosure
				119:2 U 12-slot 3.5-inch smart SAS disk enclosure
				120:2 U 36-slot smart NVMe disk enclosure
				122:2 U 2-controller 25-slot 2.5-inch NVMe controller enclosure"
			::= { hwInfoEnclosureEntry 7 }
		
		-- 1.3.6.1.4.1.34774.4.1.23.5.6.1.8
		hwInfoEnclosureTemperature OBJECT-TYPE
			SYNTAX Integer32
			MAX-ACCESS read-only
			STATUS current
			DESCRIPTION
				"Enclosure temperature (unit: ºC)."
			::= { hwInfoEnclosureEntry 8 }
		
		-- 1.3.6.1.4.1.34774.4.1.23.5.6.1.9
		hwInfoEnclosureSN OBJECT-TYPE
			SYNTAX OCTET STRING
			MAX-ACCESS read-only
			STATUS current
			DESCRIPTION
				"Enclosure SN."
			::= { hwInfoEnclosureEntry 9 }
		
		-- 1.3.6.1.4.1.34774.4.1.23.5.6.1.10
		hwInfoEnclosureMAC OBJECT-TYPE
			SYNTAX OCTET STRING
			MAX-ACCESS read-only
			STATUS current
			DESCRIPTION
				"MAC address of an enclosure."
			::= { hwInfoEnclosureEntry 10 }
		
		-- 1.3.6.1.4.1.34774.4.1.23.5.6.1.11
		hwInfoEnclosureHeight OBJECT-TYPE
			SYNTAX Unsigned32
			MAX-ACCESS read-only
			STATUS current
			DESCRIPTION
				"Enclosure height (unit: U)."
			::= { hwInfoEnclosureEntry 11 }
		
		-- 1.3.6.1.4.1.34774.4.1.23.5.6.1.12
		hwInfoEnclosureExpansionDepth OBJECT-TYPE
			SYNTAX Unsigned32
			MAX-ACCESS read-only
			STATUS current
			DESCRIPTION
				"Number of cascaded enclosures."
			::= { hwInfoEnclosureEntry 12 }
		
		-- 1.3.6.1.4.1.34774.4.1.23.5.6.1.13
		hwInfoEnclosureElectronicLabel OBJECT-TYPE
			SYNTAX OCTET STRING
			MAX-ACCESS read-only
			STATUS current
			DESCRIPTION
				"Electronic label of an enclosure."
			::= { hwInfoEnclosureEntry 13 }
		
		-- 1.3.6.1.4.1.34774.4.1.23.5.7
		hwInfoPortComTable OBJECT-TYPE
			SYNTAX SEQUENCE OF HwInfoPortComEntry
			MAX-ACCESS not-accessible
			STATUS current
			DESCRIPTION
				"This table is used to check the serial port information about a device."
			::= { hwHardwareInfo 7 }
		
		-- 1.3.6.1.4.1.34774.4.1.23.5.7.1
		hwInfoPortComEntry OBJECT-TYPE
			SYNTAX HwInfoPortComEntry
			MAX-ACCESS not-accessible
			STATUS current
			DESCRIPTION
				"A table containing the part component."
			INDEX { hwInfoPortComID }
			::= { hwInfoPortComTable 1 }
		
		HwInfoPortComEntry ::=
			SEQUENCE { 
				hwInfoPortComID
					OCTET STRING,
				hwInfoPortComLocation
					OCTET STRING,
				hwInfoPortComHealthStatus
					Unsigned32,
				hwInfoPortComRunningStatus
					Unsigned32,
				hwInfoPortComType
					Unsigned32
			 }

		-- 1.3.6.1.4.1.34774.4.1.23.5.7.1.1
		hwInfoPortComID OBJECT-TYPE
			SYNTAX OCTET STRING
			MAX-ACCESS read-only
			STATUS current
			DESCRIPTION
				"ID of a serial port, table index."
			::= { hwInfoPortComEntry 1 }
		
		-- 1.3.6.1.4.1.34774.4.1.23.5.7.1.2
		hwInfoPortComLocation OBJECT-TYPE
			SYNTAX OCTET STRING
			MAX-ACCESS read-only
			STATUS current
			DESCRIPTION
				"Location of a serial port."
			::= { hwInfoPortComEntry 2 }
		
		-- 1.3.6.1.4.1.34774.4.1.23.5.7.1.3
		hwInfoPortComHealthStatus OBJECT-TYPE
			SYNTAX Unsigned32
			MAX-ACCESS read-only
			STATUS current
			DESCRIPTION
				"Health status of a serial port. For details, see:
				1 Normal
				2 Fault
				3 Pre-Fail
				4 Partially Broken
				5 Degraded
				6 Bad Sectors Found
				7 Bit Errors Found
				8 Consistent
				9 Inconsistent
				10 Busy
				11 No Input
				12 Low Battery
				13 Single Link Fault
				14 Invalid
				15 Write Protect
				16 single link
				17 No Redundant Link
				18 Offline"
			::= { hwInfoPortComEntry 3 }
		
		-- 1.3.6.1.4.1.34774.4.1.23.5.7.1.4
		hwInfoPortComRunningStatus OBJECT-TYPE
			SYNTAX Unsigned32
			MAX-ACCESS read-only
			STATUS current
			DESCRIPTION
				"Operating status of a serial port. For details, see:
				1: Normal
				2: Running
				3: Not running
				4: Not existed
				5: Sleep in high temperature
				6: Starting
				7: Power failure rotection
				8: Spin down
				9: Started
				10: Link Up
				11: Link Down
				12: Powering on
				13: Powered off
				14: Pre-copy
				15: Copyback
				16: Reconstruction
				17: Expansion
				18: Unformatted
				19: Formatting
				20: Unmapped
				21: Initial synchronizing
				22: Consistent
				23: Synchronizing
				24: Synchronized
				25: Unsynchronized
				26: Split
				27: Online
				28: Offline
				29: Locked
				30: Enabled
				31: Disabled
				32: Balancing
				33: To be recovered
				34: Interrupted
				35: Invalid
				36: Not start
				37: Queuing
				38: Stopped
				39: Copying
				40: Completed
				41: Paused
				42: Reverse synchronizing
				43: Activated
				44: Restore
				45: Inactive
				46: Idle
				47: Powering off
				48: Charging
				49: Charging completed
				50: Discharging
				51: Upgrading
				52: Power Lost
				53: Initializing
				54: Apply change
				55: Online disable
				56: Offline disable
				57: Online frozen
				58: Offline frozen
				59: Closed
				60: Removing
				61: In service
				62: Out of service
				63: Running normal
				64: Running fail
				65: Running success
				66: Running success
				67: Running failed
				68: Waiting
				69: Canceling
				70: Canceled
				71: About to synchronize
				72: Synchronizing data
				73: Failed to synchronize
				74: Fault
				75: Migrating
				76: Migrated
				77: Activating
				78: Deactivating
				79: Start failed
				80: Stop failed
				81: Decommissioning
				82: Decommissioned
				83: Recommissioning
				84: Replacing node
				85: Scheduling
				86: Pausing
				87: Suspending
				88: Suspended
				89: Overload
				90: To be switch
				91: Switching
				92: To be cleanup
				93: Forced start
				94: Error
				95: Job completed
				96: Partition Migrating
				97: Mount
				98: Umount
				99: INSTALLING
				100: To Be Synchronized
				101: Connecting
				102: Service Switching
				103: Power-on failed
				104: REPAIRING
				105: abnormal
				106: Deleting
				107: Modifying
				108: Running(clearing data)
				109: Running(synchronizing data)
				110: Standby
				111: STOPPING
				112: RESTORE FAULT
				113: Cut Over
				114: Erasing
				115: Verifying
				119: Creating"
			::= { hwInfoPortComEntry 4 }
		
		-- 1.3.6.1.4.1.34774.4.1.23.5.7.1.5
		hwInfoPortComType OBJECT-TYPE
			SYNTAX Unsigned32
			MAX-ACCESS read-only
			STATUS current
			DESCRIPTION
				"Logical type of a serial port. For details, see:
				0: HOST
				1: EXP
				2: MNGT
				3: INNER
				4: MAINTENANCE
				5: MNGT_SRV
				6: MAINTENANCE_SRV
				7: BACKUP_MGR
				8: PRODUCT_STORAGE
				9: BACKUP_STORAGE
				10: ETH_NOT_CONFIG
				11: IP_SCALE_OUT"
			::= { hwInfoPortComEntry 5 }
		
		-- 1.3.6.1.4.1.34774.4.1.23.5.8
		hwInfoPortEthTable OBJECT-TYPE
			SYNTAX SEQUENCE OF HwInfoPortEthEntry
			MAX-ACCESS not-accessible
			STATUS current
			DESCRIPTION
				"This table is used to check the Ethernet port information about a device."
			::= { hwHardwareInfo 8 }
		
		-- 1.3.6.1.4.1.34774.4.1.23.5.8.1
		hwInfoPortEthEntry OBJECT-TYPE
			SYNTAX HwInfoPortEthEntry
			MAX-ACCESS not-accessible
			STATUS current
			DESCRIPTION
				"A table containing the part component."
			INDEX { hwInfoPortEthID }
			::= { hwInfoPortEthTable 1 }
		
		HwInfoPortEthEntry ::=
			SEQUENCE { 
				hwInfoPortEthID
					OCTET STRING,
				hwInfoPortEthLocation
					OCTET STRING,
				hwInfoPortEthHealthStatus
					Unsigned32,
				hwInfoPortEthRunningStatus
					Unsigned32,
				hwInfoPortEthType
					Unsigned32,
				hwInfoPortEthIPv4Address
					OCTET STRING,
				hwInfoPortEthSubnetMask
					OCTET STRING,
				hwInfoPortEthIPv4Gateway
					OCTET STRING,
				hwInfoPortEthIPv6Address
					OCTET STRING,
				hwInfoPortEthIPv6PrefixLength
					OCTET STRING,
				hwInfoPortEthIPv6Gateway
					OCTET STRING,
				hwInfoPortEthMAC
					OCTET STRING,
				hwInfoPortEthRole
					Unsigned32,
				hwInfoPortEthMode
					Unsigned32,
				hwInfoPortEthMTU
					Unsigned32,
				hwInfoPortEthWorkingRate
					Unsigned32,
				hwInfoPortEthBondName
					OCTET STRING,
				hwInfoPortEthiSCSIPort
					OCTET STRING,
				hwInfoPortEthiSCSIName
					OCTET STRING,
				hwInfoPortEthErrorPackets
					Unsigned32,
				hwInfoPortEthLostPackages
					Unsigned32,
				hwInfoPortEthStartTime
					OCTET STRING
			 }

		-- 1.3.6.1.4.1.34774.4.1.23.5.8.1.1
		hwInfoPortEthID OBJECT-TYPE
			SYNTAX OCTET STRING
			MAX-ACCESS read-only
			STATUS current
			DESCRIPTION
				"ID of an Ethernet port, table index."
			::= { hwInfoPortEthEntry 1 }
		
		-- 1.3.6.1.4.1.34774.4.1.23.5.8.1.2
		hwInfoPortEthLocation OBJECT-TYPE
			SYNTAX OCTET STRING
			MAX-ACCESS read-only
			STATUS current
			DESCRIPTION
				"Location of an Ethernet port."
			::= { hwInfoPortEthEntry 2 }
		
		-- 1.3.6.1.4.1.34774.4.1.23.5.8.1.3
		hwInfoPortEthHealthStatus OBJECT-TYPE
			SYNTAX Unsigned32
			MAX-ACCESS read-only
			STATUS current
			DESCRIPTION
				"Health status of an Ethernet port. For details, see:
				1 Normal
				2 Fault
				3 Pre-Fail
				4 Partially Broken
				5 Degraded
				6 Bad Sectors Found
				7 Bit Errors Found
				8 Consistent
				9 Inconsistent
				10 Busy
				11 No Input
				12 Low Battery
				13 Single Link Fault
				14 Invalid
				15 Write Protect
				16 single link
				17 No Redundant Link
				18 Offline"
			::= { hwInfoPortEthEntry 3 }
		
		-- 1.3.6.1.4.1.34774.4.1.23.5.8.1.4
		hwInfoPortEthRunningStatus OBJECT-TYPE
			SYNTAX Unsigned32
			MAX-ACCESS read-only
			STATUS current
			DESCRIPTION
				"Operating status of an Ethernet port. For details, see:
				1: Normal
				2: Running
				3: Not running
				4: Not existed
				5: Sleep in high temperature
				6: Starting
				7: Power failure rotection
				8: Spin down
				9: Started
				10: Link Up
				11: Link Down
				12: Powering on
				13: Powered off
				14: Pre-copy
				15: Copyback
				16: Reconstruction
				17: Expansion
				18: Unformatted
				19: Formatting
				20: Unmapped
				21: Initial synchronizing
				22: Consistent
				23: Synchronizing
				24: Synchronized
				25: Unsynchronized
				26: Split
				27: Online
				28: Offline
				29: Locked
				30: Enabled
				31: Disabled
				32: Balancing
				33: To be recovered
				34: Interrupted
				35: Invalid
				36: Not start
				37: Queuing
				38: Stopped
				39: Copying
				40: Completed
				41: Paused
				42: Reverse synchronizing
				43: Activated
				44: Restore
				45: Inactive
				46: Idle
				47: Powering off
				48: Charging
				49: Charging completed
				50: Discharging
				51: Upgrading
				52: Power Lost
				53: Initializing
				54: Apply change
				55: Online disable
				56: Offline disable
				57: Online frozen
				58: Offline frozen
				59: Closed
				60: Removing
				61: In service
				62: Out of service
				63: Running normal
				64: Running fail
				65: Running success
				66: Running success
				67: Running failed
				68: Waiting
				69: Canceling
				70: Canceled
				71: About to synchronize
				72: Synchronizing data
				73: Failed to synchronize
				74: Fault
				75: Migrating
				76: Migrated
				77: Activating
				78: Deactivating
				79: Start failed
				80: Stop failed
				81: Decommissioning
				82: Decommissioned
				83: Recommissioning
				84: Replacing node
				85: Scheduling
				86: Pausing
				87: Suspending
				88: Suspended
				89: Overload
				90: To be switch
				91: Switching
				92: To be cleanup
				93: Forced start
				94: Error
				95: Job completed
				96: Partition Migrating
				97: Mount
				98: Umount
				99: INSTALLING
				100: To Be Synchronized
				101: Connecting
				102: Service Switching
				103: Power-on failed
				104: REPAIRING
				105: abnormal
				106: Deleting
				107: Modifying
				108: Running(clearing data)
				109: Running(synchronizing data)
				110: Standby
				111: STOPPING
				112: RESTORE FAULT
				113: Cut Over
				114: Erasing
				115: Verifying
				119: Creating"
			::= { hwInfoPortEthEntry 4 }
		
		-- 1.3.6.1.4.1.34774.4.1.23.5.8.1.5
		hwInfoPortEthType OBJECT-TYPE
			SYNTAX Unsigned32
			MAX-ACCESS read-only
			STATUS current
			DESCRIPTION
				"Logical type of an Ethernet port. For details, see:
				0: HOST
				1: EXP
				2: MNGT
				3: INNER
				4: MAINTENANCE
				5: MNGT_SRV
				6: MAINTENANCE_SRV
				7: BACKUP_MGR
				8: PRODUCT_STORAGE
				9: BACKUP_STORAGE
				10: ETH_NOT_CONFIG
				11: IP_SCALE_OUT"
			::= { hwInfoPortEthEntry 5 }
		
		-- 1.3.6.1.4.1.34774.4.1.23.5.8.1.6
		hwInfoPortEthIPv4Address OBJECT-TYPE
			SYNTAX OCTET STRING
			MAX-ACCESS read-only
			STATUS current
			DESCRIPTION
				"IPv4 address of an Ethernet port."
			::= { hwInfoPortEthEntry 6 }
		
		-- 1.3.6.1.4.1.34774.4.1.23.5.8.1.7
		hwInfoPortEthSubnetMask OBJECT-TYPE
			SYNTAX OCTET STRING
			MAX-ACCESS read-only
			STATUS current
			DESCRIPTION
				"IPv4 mask of an Ethernet port."
			::= { hwInfoPortEthEntry 7 }
		
		-- 1.3.6.1.4.1.34774.4.1.23.5.8.1.8
		hwInfoPortEthIPv4Gateway OBJECT-TYPE
			SYNTAX OCTET STRING
			MAX-ACCESS read-only
			STATUS current
			DESCRIPTION
				"IPv4 gateway of an Ethernet port."
			::= { hwInfoPortEthEntry 8 }
		
		-- 1.3.6.1.4.1.34774.4.1.23.5.8.1.9
		hwInfoPortEthIPv6Address OBJECT-TYPE
			SYNTAX OCTET STRING
			MAX-ACCESS read-only
			STATUS current
			DESCRIPTION
				"IPv6 address of an Ethernet port."
			::= { hwInfoPortEthEntry 9 }
		
		-- 1.3.6.1.4.1.34774.4.1.23.5.8.1.10
		hwInfoPortEthIPv6PrefixLength OBJECT-TYPE
			SYNTAX OCTET STRING
			MAX-ACCESS read-only
			STATUS current
			DESCRIPTION
				"IPv6 mask of an Ethernet port."
			::= { hwInfoPortEthEntry 10 }
		
		-- 1.3.6.1.4.1.34774.4.1.23.5.8.1.11
		hwInfoPortEthIPv6Gateway OBJECT-TYPE
			SYNTAX OCTET STRING
			MAX-ACCESS read-only
			STATUS current
			DESCRIPTION
				"IPv6 gateway of an Ethernet port."
			::= { hwInfoPortEthEntry 11 }
		
		-- 1.3.6.1.4.1.34774.4.1.23.5.8.1.12
		hwInfoPortEthMAC OBJECT-TYPE
			SYNTAX OCTET STRING
			MAX-ACCESS read-only
			STATUS current
			DESCRIPTION
				"MAC address of an Ethernet port."
			::= { hwInfoPortEthEntry 12 }
		
		-- 1.3.6.1.4.1.34774.4.1.23.5.8.1.13
		hwInfoPortEthRole OBJECT-TYPE
			SYNTAX Unsigned32
			MAX-ACCESS read-only
			STATUS current
			DESCRIPTION
				"Role of an Ethernet port. Possible values are:
				2: INI
				3: TGT
				4: INI_AND_TGT
				4294967295: Invalid"
			::= { hwInfoPortEthEntry 13 }
		
		-- 1.3.6.1.4.1.34774.4.1.23.5.8.1.14
		hwInfoPortEthMode OBJECT-TYPE
			SYNTAX Unsigned32
			MAX-ACCESS read-only
			STATUS current
			DESCRIPTION
				"Auto-negotiation mode of an Ethernet port. Possible values are:
				1: HALF_DUPLEX
				2: DUPLEX
				3: AUTO 
				If the parameter value is 4294967295, this parameter is invalid."
			::= { hwInfoPortEthEntry 14 }
		
		-- 1.3.6.1.4.1.34774.4.1.23.5.8.1.15
		hwInfoPortEthMTU OBJECT-TYPE
			SYNTAX Unsigned32
			MAX-ACCESS read-only
			STATUS current
			DESCRIPTION
				"Maximum transmission unit (MTU) of an Ethernet port (unit: B). 
				If the parameter value is 4294967295, this parameter is invalid."
			::= { hwInfoPortEthEntry 15 }
		
		-- 1.3.6.1.4.1.34774.4.1.23.5.8.1.16
		hwInfoPortEthWorkingRate OBJECT-TYPE
			SYNTAX Unsigned32
			MAX-ACCESS read-only
			STATUS current
			DESCRIPTION
				"Working rate of an Ethernet port (unit: Mbit/s). 
				If the parameter value is 4294967295, this parameter is invalid."
			::= { hwInfoPortEthEntry 16 }
		
		-- 1.3.6.1.4.1.34774.4.1.23.5.8.1.17
		hwInfoPortEthBondName OBJECT-TYPE
			SYNTAX OCTET STRING
			MAX-ACCESS read-only
			STATUS current
			DESCRIPTION
				"Bond name of an Ethernet port."
			::= { hwInfoPortEthEntry 17 }
		
		-- 1.3.6.1.4.1.34774.4.1.23.5.8.1.18
		hwInfoPortEthiSCSIPort OBJECT-TYPE
			SYNTAX OCTET STRING
			MAX-ACCESS read-only
			STATUS current
			DESCRIPTION
				"iSCSI port number of an Ethernet port. The port is occupied when iSCSI is enabled. The default port number is 3260."
			::= { hwInfoPortEthEntry 18 }
		
		-- 1.3.6.1.4.1.34774.4.1.23.5.8.1.19
		hwInfoPortEthiSCSIName OBJECT-TYPE
			SYNTAX OCTET STRING
			MAX-ACCESS read-only
			STATUS current
			DESCRIPTION
				"iSCSI name of an Ethernet port."
			::= { hwInfoPortEthEntry 19 }
		
		-- 1.3.6.1.4.1.34774.4.1.23.5.8.1.20
		hwInfoPortEthErrorPackets OBJECT-TYPE
			SYNTAX Unsigned32
			MAX-ACCESS read-only
			STATUS current
			DESCRIPTION
				"Number of error packets of an Ethernet port."
			::= { hwInfoPortEthEntry 20 }
		
		-- 1.3.6.1.4.1.34774.4.1.23.5.8.1.21
		hwInfoPortEthLostPackages OBJECT-TYPE
			SYNTAX Unsigned32
			MAX-ACCESS read-only
			STATUS current
			DESCRIPTION
				"Number of lost packets of an Ethernet port."
			::= { hwInfoPortEthEntry 21 }
		
		-- 1.3.6.1.4.1.34774.4.1.23.5.8.1.22
		hwInfoPortEthStartTime OBJECT-TYPE
			SYNTAX OCTET STRING
			MAX-ACCESS read-only
			STATUS current
			DESCRIPTION
				"Time when the bit error statistics of an Ethernet port starts. If "--" is returned, this parameter is invalid."
			::= { hwInfoPortEthEntry 22 }
		
		-- 1.3.6.1.4.1.34774.4.1.23.5.9
		hwInfoPortFCTable OBJECT-TYPE
			SYNTAX SEQUENCE OF HwInfoPortFCEntry
			MAX-ACCESS not-accessible
			STATUS current
			DESCRIPTION
				"This table is used to check the Fibre Channel port information about a device."
			::= { hwHardwareInfo 9 }
		
		-- 1.3.6.1.4.1.34774.4.1.23.5.9.1
		hwInfoPortFCEntry OBJECT-TYPE
			SYNTAX HwInfoPortFCEntry
			MAX-ACCESS not-accessible
			STATUS current
			DESCRIPTION
				"A table containing the part component."
			INDEX { hwInfoPortFCID }
			::= { hwInfoPortFCTable 1 }
		
		HwInfoPortFCEntry ::=
			SEQUENCE { 
				hwInfoPortFCID
					OCTET STRING,
				hwInfoPortFCLocation
					OCTET STRING,
				hwInfoPortFCHealthStatus
					Unsigned32,
				hwInfoPortFCRunningStatus
					Unsigned32,
				hwInfoPortFCType
					Unsigned32,
				hwInfoPortFCWorkingRate
					Unsigned32,
				hwInfoPortFCConfiguredSpeed
					Unsigned32,
				hwInfoPortFCWWN
					OCTET STRING,
				hwInfoPortFCRole
					Unsigned32,
				hwInfoPortFCSFPStatus
					Unsigned32,
				hwInfoPortFCWorkingMode
					Unsigned32,
				hwInfoPortFCConfiguredMode
					Unsigned32,
				hwInfoPortFCFloginDelayTimes
					Unsigned32,
				hwInfoPortFCLostSignals
					Unsigned32,
				hwInfoPortFCLinkErrorsCodes
					Unsigned32,
				hwInfoPortFCLostSynchronizations
					Unsigned32,
				hwInfoPortFCFailedConnections
					Unsigned32,
				hwInfoPortFCStartTime
					OCTET STRING
			 }

		-- 1.3.6.1.4.1.34774.4.1.23.5.9.1.1
		hwInfoPortFCID OBJECT-TYPE
			SYNTAX OCTET STRING
			MAX-ACCESS read-only
			STATUS current
			DESCRIPTION
				"ID of a Fibre Channel port, table index."
			::= { hwInfoPortFCEntry 1 }
		
		-- 1.3.6.1.4.1.34774.4.1.23.5.9.1.2
		hwInfoPortFCLocation OBJECT-TYPE
			SYNTAX OCTET STRING
			MAX-ACCESS read-only
			STATUS current
			DESCRIPTION
				"Location of a Fibre Channel port."
			::= { hwInfoPortFCEntry 2 }
		
		-- 1.3.6.1.4.1.34774.4.1.23.5.9.1.3
		hwInfoPortFCHealthStatus OBJECT-TYPE
			SYNTAX Unsigned32
			MAX-ACCESS read-only
			STATUS current
			DESCRIPTION
				"Health status of a Fibre Channel port. For details, see:
				1 Normal
				2 Fault
				3 Pre-Fail
				4 Partially Broken
				5 Degraded
				6 Bad Sectors Found
				7 Bit Errors Found
				8 Consistent
				9 Inconsistent
				10 Busy
				11 No Input
				12 Low Battery
				13 Single Link Fault
				14 Invalid
				15 Write Protect
				16 single link
				17 No Redundant Link
				18 Offline"
			::= { hwInfoPortFCEntry 3 }
		
		-- 1.3.6.1.4.1.34774.4.1.23.5.9.1.4
		hwInfoPortFCRunningStatus OBJECT-TYPE
			SYNTAX Unsigned32
			MAX-ACCESS read-only
			STATUS current
			DESCRIPTION
				"Operating status of a Fibre Channel port. For details, see:
				1: Normal
				2: Running
				3: Not running
				4: Not existed
				5: Sleep in high temperature
				6: Starting
				7: Power failure rotection
				8: Spin down
				9: Started
				10: Link Up
				11: Link Down
				12: Powering on
				13: Powered off
				14: Pre-copy
				15: Copyback
				16: Reconstruction
				17: Expansion
				18: Unformatted
				19: Formatting
				20: Unmapped
				21: Initial synchronizing
				22: Consistent
				23: Synchronizing
				24: Synchronized
				25: Unsynchronized
				26: Split
				27: Online
				28: Offline
				29: Locked
				30: Enabled
				31: Disabled
				32: Balancing
				33: To be recovered
				34: Interrupted
				35: Invalid
				36: Not start
				37: Queuing
				38: Stopped
				39: Copying
				40: Completed
				41: Paused
				42: Reverse synchronizing
				43: Activated
				44: Restore
				45: Inactive
				46: Idle
				47: Powering off
				48: Charging
				49: Charging completed
				50: Discharging
				51: Upgrading
				52: Power Lost
				53: Initializing
				54: Apply change
				55: Online disable
				56: Offline disable
				57: Online frozen
				58: Offline frozen
				59: Closed
				60: Removing
				61: In service
				62: Out of service
				63: Running normal
				64: Running fail
				65: Running success
				66: Running success
				67: Running failed
				68: Waiting
				69: Canceling
				70: Canceled
				71: About to synchronize
				72: Synchronizing data
				73: Failed to synchronize
				74: Fault
				75: Migrating
				76: Migrated
				77: Activating
				78: Deactivating
				79: Start failed
				80: Stop failed
				81: Decommissioning
				82: Decommissioned
				83: Recommissioning
				84: Replacing node
				85: Scheduling
				86: Pausing
				87: Suspending
				88: Suspended
				89: Overload
				90: To be switch
				91: Switching
				92: To be cleanup
				93: Forced start
				94: Error
				95: Job completed
				96: Partition Migrating
				97: Mount
				98: Umount
				99: INSTALLING
				100: To Be Synchronized
				101: Connecting
				102: Service Switching
				103: Power-on failed
				104: REPAIRING
				105: abnormal
				106: Deleting
				107: Modifying
				108: Running(clearing data)
				109: Running(synchronizing data)
				110: Standby
				111: STOPPING
				112: RESTORE FAULT
				113: Cut Over
				114: Erasing
				115: Verifying
				119: Creating"
			::= { hwInfoPortFCEntry 4 }
		
		-- 1.3.6.1.4.1.34774.4.1.23.5.9.1.5
		hwInfoPortFCType OBJECT-TYPE
			SYNTAX Unsigned32
			MAX-ACCESS read-only
			STATUS current
			DESCRIPTION
				"Logical type of a Fibre Channel port. For details, see:
				0: HOST
				1: EXP
				2: MNGT
				3: INNER
				4: MAINTENANCE
				5: MNGT_SRV
				6: MAINTENANCE_SRV
				7: BACKUP_MGR
				8: PRODUCT_STORAGE
				9: BACKUP_STORAGE
				10: ETH_NOT_CONFIG
				11: IP_SCALE_OUT"
			::= { hwInfoPortFCEntry 5 }
		
		-- 1.3.6.1.4.1.34774.4.1.23.5.9.1.6
		hwInfoPortFCWorkingRate OBJECT-TYPE
			SYNTAX Unsigned32
			MAX-ACCESS read-only
			STATUS current
			DESCRIPTION
				"Working rate of a Fibre Channel port (unit: Mbit/s). 
				If the parameter value is 4294967295, this parameter is invalid."
			::= { hwInfoPortFCEntry 6 }
		
		-- 1.3.6.1.4.1.34774.4.1.23.5.9.1.7
		hwInfoPortFCConfiguredSpeed OBJECT-TYPE
			SYNTAX Unsigned32
			MAX-ACCESS read-only
			STATUS current
			DESCRIPTION
				"Configured rate of a Fibre Channel port (unit: Mbit/s). 
				0 indicates autonegotiation. 4294967295 indicates invalid."
			::= { hwInfoPortFCEntry 7 }
		
		-- 1.3.6.1.4.1.34774.4.1.23.5.9.1.8
		hwInfoPortFCWWN OBJECT-TYPE
			SYNTAX OCTET STRING
			MAX-ACCESS read-only
			STATUS current
			DESCRIPTION
				"World wide name (WWN) of a Fibre Channel port."
			::= { hwInfoPortFCEntry 8 }
		
		-- 1.3.6.1.4.1.34774.4.1.23.5.9.1.9
		hwInfoPortFCRole OBJECT-TYPE
			SYNTAX Unsigned32
			MAX-ACCESS read-only
			STATUS current
			DESCRIPTION
				"Role of a Fibre Channel port. Possible values are:
				2: INI
				3: TGT
				4: INI_AND_TGT
				4294967295: Invalid"
			::= { hwInfoPortFCEntry 9 }
		
		-- 1.3.6.1.4.1.34774.4.1.23.5.9.1.10
		hwInfoPortFCSFPStatus OBJECT-TYPE
			SYNTAX Unsigned32
			MAX-ACCESS read-only
			STATUS current
			DESCRIPTION
				"Status of a Fibre Channel port. Possible values are:
				0: Not Exist
				1: Offline
				2: Online
				4294967295: Invalid"
			::= { hwInfoPortFCEntry 10 }
		
		-- 1.3.6.1.4.1.34774.4.1.23.5.9.1.11
		hwInfoPortFCWorkingMode OBJECT-TYPE
			SYNTAX Unsigned32
			MAX-ACCESS read-only
			STATUS current
			DESCRIPTION
				"Operating mode of a Fibre Channel port. Possible values are:
				0: Fabric
				1: FC-AL
				2: Point To Point
				3: Auto
				4294967295: Invalid"
			::= { hwInfoPortFCEntry 11 }
		
		-- 1.3.6.1.4.1.34774.4.1.23.5.9.1.12
		hwInfoPortFCConfiguredMode OBJECT-TYPE
			SYNTAX Unsigned32
			MAX-ACCESS read-only
			STATUS current
			DESCRIPTION
				"Configured mode of a Fibre Channel port. Possible values are:
				0: Fabric
				1: FC-AL
				2: P2P
				3: Auto
				4294967295: Invalid"
			::= { hwInfoPortFCEntry 12 }
		
		-- 1.3.6.1.4.1.34774.4.1.23.5.9.1.13
		hwInfoPortFCFloginDelayTimes OBJECT-TYPE
			SYNTAX Unsigned32
			MAX-ACCESS read-only
			STATUS current
			DESCRIPTION
				"Flogin delay of a Fibre Channel port (unit: ms)."
			::= { hwInfoPortFCEntry 13 }
		
		-- 1.3.6.1.4.1.34774.4.1.23.5.9.1.14
		hwInfoPortFCLostSignals OBJECT-TYPE
			SYNTAX Unsigned32
			MAX-ACCESS read-only
			STATUS current
			DESCRIPTION
				"Number of Loss of Signal errors of a Fibre Channel port."
			::= { hwInfoPortFCEntry 14 }
		
		-- 1.3.6.1.4.1.34774.4.1.23.5.9.1.15
		hwInfoPortFCLinkErrorsCodes OBJECT-TYPE
			SYNTAX Unsigned32
			MAX-ACCESS read-only
			STATUS current
			DESCRIPTION
				"Number of Bad RX Char errors of a Fibre Channel port."
			::= { hwInfoPortFCEntry 15 }
		
		-- 1.3.6.1.4.1.34774.4.1.23.5.9.1.16
		hwInfoPortFCLostSynchronizations OBJECT-TYPE
			SYNTAX Unsigned32
			MAX-ACCESS read-only
			STATUS current
			DESCRIPTION
				"Number of Loss of Sync errors of a Fibre Channel port."
			::= { hwInfoPortFCEntry 16 }
		
		-- 1.3.6.1.4.1.34774.4.1.23.5.9.1.17
		hwInfoPortFCFailedConnections OBJECT-TYPE
			SYNTAX Unsigned32
			MAX-ACCESS read-only
			STATUS current
			DESCRIPTION
				"Number of Link Fail errors of a Fibre Channel port."
			::= { hwInfoPortFCEntry 17 }
		
		-- 1.3.6.1.4.1.34774.4.1.23.5.9.1.18
		hwInfoPortFCStartTime OBJECT-TYPE
			SYNTAX OCTET STRING
			MAX-ACCESS read-only
			STATUS current
			DESCRIPTION
				"Time when the bit error statistics of a Fibre Channel port starts. If "--" is returned, this parameter is invalid."
			::= { hwInfoPortFCEntry 18 }
		
		-- 1.3.6.1.4.1.34774.4.1.23.5.11
		hwInfoPortPCIETable OBJECT-TYPE
			SYNTAX SEQUENCE OF HwInfoPortPCIEEntry
			MAX-ACCESS not-accessible
			STATUS current
			DESCRIPTION
				"This table is used to check the PCIe port information about a device."
			::= { hwHardwareInfo 11 }
		
		-- 1.3.6.1.4.1.34774.4.1.23.5.11.1
		hwInfoPortPCIEEntry OBJECT-TYPE
			SYNTAX HwInfoPortPCIEEntry
			MAX-ACCESS not-accessible
			STATUS current
			DESCRIPTION
				"A table containing the part component."
			INDEX { hwInfoPortPCIEID }
			::= { hwInfoPortPCIETable 1 }
		
		HwInfoPortPCIEEntry ::=
			SEQUENCE { 
				hwInfoPortPCIEID
					OCTET STRING,
				hwInfoPortPCIELocation
					OCTET STRING,
				hwInfoPortPCIEHealthStatus
					Unsigned32,
				hwInfoPortPCIERunningStatus
					Unsigned32,
				hwInfoPortPCIESpeed
					Unsigned32,
				hwInfoPortPCIECurrentPeerPortID
					OCTET STRING,
				hwInfoPortPCIESuggestPeerPortID
					OCTET STRING,
				hwInfoPortPCIELostSignals
					Unsigned32,
				hwInfoPortPCIEECRCError
					Unsigned32,
				hwInfoPortPCIEBadTlp
					Unsigned32,
				hwInfoPortPCIEBadDllp
					Unsigned32,
				hwInfoPortPCIERecvError
					Unsigned32,
				hwInfoPortPCIEChipEccError
					Unsigned32,
				hwInfoPortPCIEStartTime
					OCTET STRING
			 }

		-- 1.3.6.1.4.1.34774.4.1.23.5.11.1.1
		hwInfoPortPCIEID OBJECT-TYPE
			SYNTAX OCTET STRING
			MAX-ACCESS read-only
			STATUS current
			DESCRIPTION
				"ID of a PCIe port, table index."
			::= { hwInfoPortPCIEEntry 1 }
		
		-- 1.3.6.1.4.1.34774.4.1.23.5.11.1.2
		hwInfoPortPCIELocation OBJECT-TYPE
			SYNTAX OCTET STRING
			MAX-ACCESS read-only
			STATUS current
			DESCRIPTION
				"Location of a PCIe port."
			::= { hwInfoPortPCIEEntry 2 }
		
		-- 1.3.6.1.4.1.34774.4.1.23.5.11.1.3
		hwInfoPortPCIEHealthStatus OBJECT-TYPE
			SYNTAX Unsigned32
			MAX-ACCESS read-only
			STATUS current
			DESCRIPTION
				"Health status of a PCIe port. For details, see:
				1 Normal
				2 Fault
				3 Pre-Fail
				4 Partially Broken
				5 Degraded
				6 Bad Sectors Found
				7 Bit Errors Found
				8 Consistent
				9 Inconsistent
				10 Busy
				11 No Input
				12 Low Battery
				13 Single Link Fault
				14 Invalid
				15 Write Protect
				16 single link
				17 No Redundant Link
				18 Offline"
			::= { hwInfoPortPCIEEntry 3 }
		
		-- 1.3.6.1.4.1.34774.4.1.23.5.11.1.4
		hwInfoPortPCIERunningStatus OBJECT-TYPE
			SYNTAX Unsigned32
			MAX-ACCESS read-only
			STATUS current
			DESCRIPTION
				"Operating status of a PCIe port. For details, see:
				1: Normal
				2: Running
				3: Not running
				4: Not existed
				5: Sleep in high temperature
				6: Starting
				7: Power failure rotection
				8: Spin down
				9: Started
				10: Link Up
				11: Link Down
				12: Powering on
				13: Powered off
				14: Pre-copy
				15: Copyback
				16: Reconstruction
				17: Expansion
				18: Unformatted
				19: Formatting
				20: Unmapped
				21: Initial synchronizing
				22: Consistent
				23: Synchronizing
				24: Synchronized
				25: Unsynchronized
				26: Split
				27: Online
				28: Offline
				29: Locked
				30: Enabled
				31: Disabled
				32: Balancing
				33: To be recovered
				34: Interrupted
				35: Invalid
				36: Not start
				37: Queuing
				38: Stopped
				39: Copying
				40: Completed
				41: Paused
				42: Reverse synchronizing
				43: Activated
				44: Restore
				45: Inactive
				46: Idle
				47: Powering off
				48: Charging
				49: Charging completed
				50: Discharging
				51: Upgrading
				52: Power Lost
				53: Initializing
				54: Apply change
				55: Online disable
				56: Offline disable
				57: Online frozen
				58: Offline frozen
				59: Closed
				60: Removing
				61: In service
				62: Out of service
				63: Running normal
				64: Running fail
				65: Running success
				66: Running success
				67: Running failed
				68: Waiting
				69: Canceling
				70: Canceled
				71: About to synchronize
				72: Synchronizing data
				73: Failed to synchronize
				74: Fault
				75: Migrating
				76: Migrated
				77: Activating
				78: Deactivating
				79: Start failed
				80: Stop failed
				81: Decommissioning
				82: Decommissioned
				83: Recommissioning
				84: Replacing node
				85: Scheduling
				86: Pausing
				87: Suspending
				88: Suspended
				89: Overload
				90: To be switch
				91: Switching
				92: To be cleanup
				93: Forced start
				94: Error
				95: Job completed
				96: Partition Migrating
				97: Mount
				98: Umount
				99: INSTALLING
				100: To Be Synchronized
				101: Connecting
				102: Service Switching
				103: Power-on failed
				104: REPAIRING
				105: abnormal
				106: Deleting
				107: Modifying
				108: Running(clearing data)
				109: Running(synchronizing data)
				110: Standby
				111: STOPPING
				112: RESTORE FAULT
				113: Cut Over
				114: Erasing
				115: Verifying
				119: Creating"
			::= { hwInfoPortPCIEEntry 4 }
		
		-- 1.3.6.1.4.1.34774.4.1.23.5.11.1.5
		hwInfoPortPCIESpeed OBJECT-TYPE
			SYNTAX Unsigned32
			MAX-ACCESS read-only
			STATUS current
			DESCRIPTION
				"Data transmission rate of a PCIe port (unit: Mbit/s)."
			::= { hwInfoPortPCIEEntry 5 }
		
		-- 1.3.6.1.4.1.34774.4.1.23.5.11.1.6
		hwInfoPortPCIECurrentPeerPortID OBJECT-TYPE
			SYNTAX OCTET STRING
			MAX-ACCESS read-only
			STATUS current
			DESCRIPTION
				"ID of the port connecting to a PCIe port."
			::= { hwInfoPortPCIEEntry 6 }
		
		-- 1.3.6.1.4.1.34774.4.1.23.5.11.1.7
		hwInfoPortPCIESuggestPeerPortID OBJECT-TYPE
			SYNTAX OCTET STRING
			MAX-ACCESS read-only
			STATUS current
			DESCRIPTION
				"ID of the port that is supposed to connect to a PCIe port."
			::= { hwInfoPortPCIEEntry 7 }
		
		-- 1.3.6.1.4.1.34774.4.1.23.5.11.1.8
		hwInfoPortPCIELostSignals OBJECT-TYPE
			SYNTAX Unsigned32
			MAX-ACCESS read-only
			STATUS current
			DESCRIPTION
				"Number of bit errors of a PCIe port."
			::= { hwInfoPortPCIEEntry 8 }
		
		-- 1.3.6.1.4.1.34774.4.1.23.5.11.1.9
		hwInfoPortPCIEECRCError OBJECT-TYPE
			SYNTAX Unsigned32
			MAX-ACCESS read-only
			STATUS current
			DESCRIPTION
				"Number of ECRC errors of a PCIe port."
			::= { hwInfoPortPCIEEntry 9 }
		
		-- 1.3.6.1.4.1.34774.4.1.23.5.11.1.10
		hwInfoPortPCIEBadTlp OBJECT-TYPE
			SYNTAX Unsigned32
			MAX-ACCESS read-only
			STATUS current
			DESCRIPTION
				"Number of bad TLPs of a PCIe port."
			::= { hwInfoPortPCIEEntry 10 }
		
		-- 1.3.6.1.4.1.34774.4.1.23.5.11.1.11
		hwInfoPortPCIEBadDllp OBJECT-TYPE
			SYNTAX Unsigned32
			MAX-ACCESS read-only
			STATUS current
			DESCRIPTION
				"Number of bad DLLPs of a PCIe port."
			::= { hwInfoPortPCIEEntry 11 }
		
		-- 1.3.6.1.4.1.34774.4.1.23.5.11.1.12
		hwInfoPortPCIERecvError OBJECT-TYPE
			SYNTAX Unsigned32
			MAX-ACCESS read-only
			STATUS current
			DESCRIPTION
				"Number of receiver errors of a PCIe port."
			::= { hwInfoPortPCIEEntry 12 }
		
		-- 1.3.6.1.4.1.34774.4.1.23.5.11.1.13
		hwInfoPortPCIEChipEccError OBJECT-TYPE
			SYNTAX Unsigned32
			MAX-ACCESS read-only
			STATUS current
			DESCRIPTION
				"Number of chip ECC errors of a PCIe port."
			::= { hwInfoPortPCIEEntry 13 }
		
		-- 1.3.6.1.4.1.34774.4.1.23.5.11.1.14
		hwInfoPortPCIEStartTime OBJECT-TYPE
			SYNTAX OCTET STRING
			MAX-ACCESS read-only
			STATUS current
			DESCRIPTION
				"Time when the bit error statistics of a PCIe port starts. 
				If "--" is returned, this parameter is invalid."
			::= { hwInfoPortPCIEEntry 14 }
		
		-- 1.3.6.1.4.1.34774.4.1.23.5.12
		hwInfoPortSASTable OBJECT-TYPE
			SYNTAX SEQUENCE OF HwInfoPortSASEntry
			MAX-ACCESS not-accessible
			STATUS current
			DESCRIPTION
				"This table is used to check the SAS port information about a device."
			::= { hwHardwareInfo 12 }
		
		-- 1.3.6.1.4.1.34774.4.1.23.5.12.1
		hwInfoPortSASEntry OBJECT-TYPE
			SYNTAX HwInfoPortSASEntry
			MAX-ACCESS not-accessible
			STATUS current
			DESCRIPTION
				"A table containing the part component."
			INDEX { hwInfoPortSASID }
			::= { hwInfoPortSASTable 1 }
		
		HwInfoPortSASEntry ::=
			SEQUENCE { 
				hwInfoPortSASID
					OCTET STRING,
				hwInfoPortSASLocation
					OCTET STRING,
				hwInfoPortSASHealthStatus
					Unsigned32,
				hwInfoPortSASRunningStatus
					Unsigned32,
				hwInfoPortSASType
					Unsigned32,
				hwInfoPortSASWorkingRate
					Unsigned32,
				hwInfoPortSASWWN
					OCTET STRING,
				hwInfoPortSASRole
					Unsigned32,
				hwInfoPortSASInvalidDword
					Unsigned32,
				hwInfoPortSASConsistErrors
					Unsigned32,
				hwInfoPortSASLossOfDword
					Unsigned32,
				hwInfoPortSASPHYResetErrors
					Unsigned32,
				hwInfoPortSASStartTime
					OCTET STRING,
				hwInfoPortSASEnabled
					Unsigned32
			 }

		-- 1.3.6.1.4.1.34774.4.1.23.5.12.1.1
		hwInfoPortSASID OBJECT-TYPE
			SYNTAX OCTET STRING
			MAX-ACCESS read-only
			STATUS current
			DESCRIPTION
				"ID of a SAS port, table index."
			::= { hwInfoPortSASEntry 1 }
		
		-- 1.3.6.1.4.1.34774.4.1.23.5.12.1.2
		hwInfoPortSASLocation OBJECT-TYPE
			SYNTAX OCTET STRING
			MAX-ACCESS read-only
			STATUS current
			DESCRIPTION
				"Location of a SAS port."
			::= { hwInfoPortSASEntry 2 }
		
		-- 1.3.6.1.4.1.34774.4.1.23.5.12.1.3
		hwInfoPortSASHealthStatus OBJECT-TYPE
			SYNTAX Unsigned32
			MAX-ACCESS read-only
			STATUS current
			DESCRIPTION
				"Health status of a SAS port. For details, see:
				1 Normal
				2 Fault
				3 Pre-Fail
				4 Partially Broken
				5 Degraded
				6 Bad Sectors Found
				7 Bit Errors Found
				8 Consistent
				9 Inconsistent
				10 Busy
				11 No Input
				12 Low Battery
				13 Single Link Fault
				14 Invalid
				15 Write Protect
				16 single link
				17 No Redundant Link
				18 Offline"
			::= { hwInfoPortSASEntry 3 }
		
		-- 1.3.6.1.4.1.34774.4.1.23.5.12.1.4
		hwInfoPortSASRunningStatus OBJECT-TYPE
			SYNTAX Unsigned32
			MAX-ACCESS read-only
			STATUS current
			DESCRIPTION
				"Operating status of a SAS port. For details, see:
				1: Normal
				2: Running
				3: Not running
				4: Not existed
				5: Sleep in high temperature
				6: Starting
				7: Power failure rotection
				8: Spin down
				9: Started
				10: Link Up
				11: Link Down
				12: Powering on
				13: Powered off
				14: Pre-copy
				15: Copyback
				16: Reconstruction
				17: Expansion
				18: Unformatted
				19: Formatting
				20: Unmapped
				21: Initial synchronizing
				22: Consistent
				23: Synchronizing
				24: Synchronized
				25: Unsynchronized
				26: Split
				27: Online
				28: Offline
				29: Locked
				30: Enabled
				31: Disabled
				32: Balancing
				33: To be recovered
				34: Interrupted
				35: Invalid
				36: Not start
				37: Queuing
				38: Stopped
				39: Copying
				40: Completed
				41: Paused
				42: Reverse synchronizing
				43: Activated
				44: Restore
				45: Inactive
				46: Idle
				47: Powering off
				48: Charging
				49: Charging completed
				50: Discharging
				51: Upgrading
				52: Power Lost
				53: Initializing
				54: Apply change
				55: Online disable
				56: Offline disable
				57: Online frozen
				58: Offline frozen
				59: Closed
				60: Removing
				61: In service
				62: Out of service
				63: Running normal
				64: Running fail
				65: Running success
				66: Running success
				67: Running failed
				68: Waiting
				69: Canceling
				70: Canceled
				71: About to synchronize
				72: Synchronizing data
				73: Failed to synchronize
				74: Fault
				75: Migrating
				76: Migrated
				77: Activating
				78: Deactivating
				79: Start failed
				80: Stop failed
				81: Decommissioning
				82: Decommissioned
				83: Recommissioning
				84: Replacing node
				85: Scheduling
				86: Pausing
				87: Suspending
				88: Suspended
				89: Overload
				90: To be switch
				91: Switching
				92: To be cleanup
				93: Forced start
				94: Error
				95: Job completed
				96: Partition Migrating
				97: Mount
				98: Umount
				99: INSTALLING
				100: To Be Synchronized
				101: Connecting
				102: Service Switching
				103: Power-on failed
				104: REPAIRING
				105: abnormal
				106: Deleting
				107: Modifying
				108: Running(clearing data)
				109: Running(synchronizing data)
				110: Standby
				111: STOPPING
				112: RESTORE FAULT
				113: Cut Over
				114: Erasing
				115: Verifying
				119: Creating"
			::= { hwInfoPortSASEntry 4 }
		
		-- 1.3.6.1.4.1.34774.4.1.23.5.12.1.5
		hwInfoPortSASType OBJECT-TYPE
			SYNTAX Unsigned32
			MAX-ACCESS read-only
			STATUS current
			DESCRIPTION
				"Logical type of a SAS port. For details, see:
				0: HOST
				1: EXP
				2: MNGT
				3: INNER
				4: MAINTENANCE
				5: MNGT_SRV
				6: MAINTENANCE_SRV
				7: BACKUP_MGR
				8: PRODUCT_STORAGE
				9: BACKUP_STORAGE
				10: ETH_NOT_CONFIG
				11: IP_SCALE_OUT"
			::= { hwInfoPortSASEntry 5 }
		
		-- 1.3.6.1.4.1.34774.4.1.23.5.12.1.6
		hwInfoPortSASWorkingRate OBJECT-TYPE
			SYNTAX Unsigned32
			MAX-ACCESS read-only
			STATUS current
			DESCRIPTION
				"Working rate of a SAS port (unit: Mbit/s). 
				If the parameter value is 4294967295, this parameter is invalid."
			::= { hwInfoPortSASEntry 6 }
		
		-- 1.3.6.1.4.1.34774.4.1.23.5.12.1.7
		hwInfoPortSASWWN OBJECT-TYPE
			SYNTAX OCTET STRING
			MAX-ACCESS read-only
			STATUS current
			DESCRIPTION
				"WWN of a SAS port."
			::= { hwInfoPortSASEntry 7 }
		
		-- 1.3.6.1.4.1.34774.4.1.23.5.12.1.8
		hwInfoPortSASRole OBJECT-TYPE
			SYNTAX Unsigned32
			MAX-ACCESS read-only
			STATUS current
			DESCRIPTION
				"Role of a SAS port. Possible values are:
				2: INI
				3: TGT
				4: INI_AND_TGT
				4294967295: Invalid"
			::= { hwInfoPortSASEntry 8 }
		
		-- 1.3.6.1.4.1.34774.4.1.23.5.12.1.9
		hwInfoPortSASInvalidDword OBJECT-TYPE
			SYNTAX Unsigned32
			MAX-ACCESS read-only
			STATUS current
			DESCRIPTION
				"Number of invalid DWORDs of a SAS port."
			::= { hwInfoPortSASEntry 9 }
		
		-- 1.3.6.1.4.1.34774.4.1.23.5.12.1.10
		hwInfoPortSASConsistErrors OBJECT-TYPE
			SYNTAX Unsigned32
			MAX-ACCESS read-only
			STATUS current
			DESCRIPTION
				"Number of consistency errors of a SAS port."
			::= { hwInfoPortSASEntry 10 }
		
		-- 1.3.6.1.4.1.34774.4.1.23.5.12.1.11
		hwInfoPortSASLossOfDword OBJECT-TYPE
			SYNTAX Unsigned32
			MAX-ACCESS read-only
			STATUS current
			DESCRIPTION
				"Number of lost DWORDs of a SAS port."
			::= { hwInfoPortSASEntry 11 }
		
		-- 1.3.6.1.4.1.34774.4.1.23.5.12.1.12
		hwInfoPortSASPHYResetErrors OBJECT-TYPE
			SYNTAX Unsigned32
			MAX-ACCESS read-only
			STATUS current
			DESCRIPTION
				"Number of physical reset errors of a SAS port."
			::= { hwInfoPortSASEntry 12 }
		
		-- 1.3.6.1.4.1.34774.4.1.23.5.12.1.13
		hwInfoPortSASStartTime OBJECT-TYPE
			SYNTAX OCTET STRING
			MAX-ACCESS read-only
			STATUS current
			DESCRIPTION
				"Time when the bit error statistics of a SAS port starts. 
				If "--" is returned, this parameter is invalid."
			::= { hwInfoPortSASEntry 13 }
		
		-- 1.3.6.1.4.1.34774.4.1.23.5.12.1.14
		hwInfoPortSASEnabled OBJECT-TYPE
			SYNTAX Unsigned32
			MAX-ACCESS read-only
			STATUS current
			DESCRIPTION
				"To determine whether a SAS port is enabled. Possible values are:
				0: No
				1: Yes"
			::= { hwInfoPortSASEntry 14 }
		
		-- 1.3.6.1.4.1.34774.4.1.23.5.13
		hwInfoInterfaceModuleTable OBJECT-TYPE
			SYNTAX SEQUENCE OF HwInfoInterfaceModuleEntry
			MAX-ACCESS not-accessible
			STATUS current
			DESCRIPTION
				"This table is used to check the interface module information about a device."
			::= { hwHardwareInfo 13 }
		
		-- 1.3.6.1.4.1.34774.4.1.23.5.13.1
		hwInfoInterfaceModuleEntry OBJECT-TYPE
			SYNTAX HwInfoInterfaceModuleEntry
			MAX-ACCESS not-accessible
			STATUS current
			DESCRIPTION
				"A table containing the part component."
			INDEX { hwInfoInterfaceModuleID }
			::= { hwInfoInterfaceModuleTable 1 }
		
		HwInfoInterfaceModuleEntry ::=
			SEQUENCE { 
				hwInfoInterfaceModuleID
					OCTET STRING,
				hwInfoInterfaceModuleLocation
					OCTET STRING,
				hwInfoInterfaceModuleHealthStatus
					Unsigned32,
				hwInfoInterfaceModuleRunningStatus
					Unsigned32,
				hwInfoInterfaceModuleModel
					Unsigned32,
				hwInfoInterfaceModuleLogicVersion
					OCTET STRING,
				hwInfoInterfaceModulePCBVersion
					OCTET STRING,
				hwInfoInterfaceModuleElectronicLabel
					OCTET STRING
			 }

		-- 1.3.6.1.4.1.34774.4.1.23.5.13.1.1
		hwInfoInterfaceModuleID OBJECT-TYPE
			SYNTAX OCTET STRING
			MAX-ACCESS read-only
			STATUS current
			DESCRIPTION
				"ID of an interface module, table index."
			::= { hwInfoInterfaceModuleEntry 1 }
		
		-- 1.3.6.1.4.1.34774.4.1.23.5.13.1.2
		hwInfoInterfaceModuleLocation OBJECT-TYPE
			SYNTAX OCTET STRING
			MAX-ACCESS read-only
			STATUS current
			DESCRIPTION
				"Location of an interface module."
			::= { hwInfoInterfaceModuleEntry 2 }
		
		-- 1.3.6.1.4.1.34774.4.1.23.5.13.1.3
		hwInfoInterfaceModuleHealthStatus OBJECT-TYPE
			SYNTAX Unsigned32
			MAX-ACCESS read-only
			STATUS current
			DESCRIPTION
				"Health status of an interface module. For details, see:
				1 Normal
				2 Fault
				3 Pre-Fail
				4 Partially Broken
				5 Degraded
				6 Bad Sectors Found
				7 Bit Errors Found
				8 Consistent
				9 Inconsistent
				10 Busy
				11 No Input
				12 Low Battery
				13 Single Link Fault
				14 Invalid
				15 Write Protect
				16 single link
				17 No Redundant Link
				18 Offline"
			::= { hwInfoInterfaceModuleEntry 3 }
		
		-- 1.3.6.1.4.1.34774.4.1.23.5.13.1.4
		hwInfoInterfaceModuleRunningStatus OBJECT-TYPE
			SYNTAX Unsigned32
			MAX-ACCESS read-only
			STATUS current
			DESCRIPTION
				"Operating status of an interface module. For details, see:
				1: Normal
				2: Running
				3: Not running
				4: Not existed
				5: Sleep in high temperature
				6: Starting
				7: Power failure rotection
				8: Spin down
				9: Started
				10: Link Up
				11: Link Down
				12: Powering on
				13: Powered off
				14: Pre-copy
				15: Copyback
				16: Reconstruction
				17: Expansion
				18: Unformatted
				19: Formatting
				20: Unmapped
				21: Initial synchronizing
				22: Consistent
				23: Synchronizing
				24: Synchronized
				25: Unsynchronized
				26: Split
				27: Online
				28: Offline
				29: Locked
				30: Enabled
				31: Disabled
				32: Balancing
				33: To be recovered
				34: Interrupted
				35: Invalid
				36: Not start
				37: Queuing
				38: Stopped
				39: Copying
				40: Completed
				41: Paused
				42: Reverse synchronizing
				43: Activated
				44: Restore
				45: Inactive
				46: Idle
				47: Powering off
				48: Charging
				49: Charging completed
				50: Discharging
				51: Upgrading
				52: Power Lost
				53: Initializing
				54: Apply change
				55: Online disable
				56: Offline disable
				57: Online frozen
				58: Offline frozen
				59: Closed
				60: Removing
				61: In service
				62: Out of service
				63: Running normal
				64: Running fail
				65: Running success
				66: Running success
				67: Running failed
				68: Waiting
				69: Canceling
				70: Canceled
				71: About to synchronize
				72: Synchronizing data
				73: Failed to synchronize
				74: Fault
				75: Migrating
				76: Migrated
				77: Activating
				78: Deactivating
				79: Start failed
				80: Stop failed
				81: Decommissioning
				82: Decommissioned
				83: Recommissioning
				84: Replacing node
				85: Scheduling
				86: Pausing
				87: Suspending
				88: Suspended
				89: Overload
				90: To be switch
				91: Switching
				92: To be cleanup
				93: Forced start
				94: Error
				95: Job completed
				96: Partition Migrating
				97: Mount
				98: Umount
				99: INSTALLING
				100: To Be Synchronized
				101: Connecting
				102: Service Switching
				103: Power-on failed
				104: REPAIRING
				105: abnormal
				106: Deleting
				107: Modifying
				108: Running(clearing data)
				109: Running(synchronizing data)
				110: Standby
				111: STOPPING
				112: RESTORE FAULT
				113: Cut Over
				114: Erasing
				115: Verifying
				119: Creating"
			::= { hwInfoInterfaceModuleEntry 4 }
		
		-- 1.3.6.1.4.1.34774.4.1.23.5.13.1.5
		hwInfoInterfaceModuleModel OBJECT-TYPE
			SYNTAX Unsigned32
			MAX-ACCESS read-only
			STATUS current
			DESCRIPTION
				"Type of an interface module. For details, see:
				1: 4 x 4 G FC Interface Module
				2: 2 x 4 G FC Interface Module
				3: 2 x GE Electrical Interface Module
				4: 4 x SAS I Interface Module
				5: Swapped FC Interface Module
				6: 2 x 10GE Optical Interface Module
				7: 1 x 8 G FC Optical Interface Module
				8: 2 x 8 G FC Optical Interface Module
				9: 2 x SAS II Electrical Interface Module
				10: 4 x SAS II Electrical Interface Module
				11: 2 x FC + 2 x GE Interface Module
				12: 4 x GE Electrical Interface Module
				13: 4 x 8 G FC Optical Interface Module
				16: 4 x mini-SAS Interface Module
				21: 4 x 10 G FCoE Optical Interface Module
				22: 2 x 6 G SAS Interface Module
				23: 2 x 6 G SAS Interface Module
				24: Management Board
				25: 4 x 10GE Interface Module
				26: PCIe Interface Module
				27: 2x10G Optical Interface Module
				28: 4xGE Optical Interface Module
				29: 2 x 16 G FC Optical Interface Module
				30: 4 x 12SAS QSFP Interface Module
				31: 4 x 10GE Electrical Interface Module
				32: 2 x 40GE Infiniband Interface Module
				33: 2 port 4*14Gb IB I/O module
				34: 4 x GE Electrical Interface Module
				35: Smart ACC module
				36: 4x10GE Electrical Interface Module
				37: 4 port SmartIO I/O module
				38: 8x8G FC Optical Interface Module
				39: 4x8G FC Optical Interface Module
				40: 4x16G FC Optical Interface Module
				41: 12 port 4*12Gb SAS Back- End Interconnect I/O Module
				42: 12 port SmartIO I/O module
				43: RoCE 10G/25G Interface Module
				44: 2-port PCIe 3.0 Interface Module
				55: 2-port 8 Gbit/s PCIe scale-up interface module
				58: 8x16G FC Optical Interface Module
				65: 4 ports SmartIO I/O module
				66: 4 ports SmartIO I/O module
				67: 2 ports 100Gb/40Gb ETH I/O module
				68: 2 ports 100Gb/40Gb ETH I/O module
				71: 4 ports 10Gb ETH I/O module
				516: 4 ports FE 1 Gbit/s ETH I/O module
				518: 4 ports BE 12 Gbit/s SAS I/O module
				529: AI Accelerator Card
				535: AI Accelerator Card
				537: 4 ports FE 1 Gbit/s ETH I/O module
				538: 4 ports BE 12 Gbit/s SAS I/O module
				580: 4 ports FE 1 Gbit/s ETH I/O module
				583: 4 ports BE 12 Gbit/s SAS V2 I/O module
				601: 4 ports FE 1 Gbit/s ETH I/O module
				2304: 4 ports FE 8 Gbit/s Fibre Channel I/O module
				2305: 4 ports FE 16 Gbit/s Fibre Channel I/O module
				2306: 4 ports FE 32 Gbit/s Fibre Channel I/O module
				2307: 4 ports FE 10 Gbit/s ETH I/O module
				2308: 4 ports FE 25 Gbit/s ETH I/O module
				2309: 4 ports SO 25 Gbit/s RDMA I/O module
				2310: 4 ports FE 8 Gbit/s Fibre Channel I/O module
				2311: 4 ports FE 16 Gbit/s Fibre Channel I/O module
				2312: 4 ports FE 32 Gbit/s Fibre Channel I/O module
				2313: 4 ports FE 10 Gbit/s ETH I/O module
				2314: 4 ports FE 25 Gbit/s ETH I/O module
				2315: 2 ports FE 40 Gbit/s ETH I/O module
				2316: 2 ports FE 100 Gbit/s ETH I/O module
				2317: 2 ports BE 100 Gbit/s RDMA I/O module
				2318: 2 ports SO 100 Gbit/s RDMA I/O module
				2319: 2 ports FE 40 Gbit/s ETH I/O module
				2320: 2 ports FE 100 Gbit/s ETH I/O module
				2321: 2 ports BE 100 Gbit/s RDMA I/O module
				2322: 2 ports SO 100 Gbit/s RDMA I/O module
				2323: 4 ports FE 10 Gbit/s ROCE I/O module
				2324: 4 ports FE 25 Gbit/s ROCE I/O module
				2325: 4 ports FE 10 Gbit/s ROCE I/O module
				2326: 4 ports FE 25 Gbit/s ROCE I/O module
				2327: 2 ports FE 40 Gbit/s ROCE I/O module
				2328: 2 ports FE 100 Gbit/s ROCE I/O module
				2329: 2 ports FE 40 Gbit/s ROCE I/O module
				2330: 2 ports FE 100 Gbit/s ROCE I/O module
				2331: 4 ports FE 10 Gbit/s ETH I/O module
				2332: 4 ports FE 10 Gbit/s ETH I/O module
				2333: 4 ports FE 8 Gbit/s Fibre Channel I/O module
				2334: 4 ports FE 16 Gbit/s Fibre Channel I/O module
				2335: 4 ports FE 32 Gbit/s Fibre Channel I/O module
				2336: 4 ports FE 10 Gbit/s ETH I/O module
				2337: 4 ports FE 25 Gbit/s ETH I/O module
				2338: 4 ports SO 25 Gbit/s RDMA I/O module
				2339: 4 ports FE 10 Gbit/s ROCE I/O module
				2340: 4 ports FE 25 Gbit/s ROCE I/O module
				2341: 4 ports FE 8 Gbit/s Fibre Channel I/O module
				2342: 4 ports FE 16 Gbit/s Fibre Channel I/O module
				2343: 4 ports FE 32 Gbit/s Fibre Channel I/O module
				2344: 4 ports FE 10 Gbit/s ETH I/O module
				2345: 4 ports FE 25 Gbit/s ETH I/O module
				2346: 4 ports FE 10 Gbit/s ROCE I/O module
				2347: 4 ports FE 25 Gbit/s ROCE I/O module
				2348: 2 ports FE 40 Gbit/s ETH I/O module
				2349: 2 ports FE 100 Gbit/s ETH I/O module
				2350: 2 ports BE 100 Gbit/s RDMA I/O module
				2351: 2 ports SO 100 Gbit/s RDMA I/O module
				2352: 2 ports FE 40 Gbit/s ROCE I/O module
				2353: 2 ports FE 100 Gbit/s ROCE I/O module
				2354: 2 ports FE 40 Gbit/s ETH I/O module
				2355: 2 ports FE 100 Gbit/s ETH I/O module
				2356: 2 ports BE 100 Gbit/s RDMA I/O module
				2357: 2 ports SO 100 Gbit/s RDMA I/O module
				2358: 2 ports FE 40 Gbit/s ROCE I/O module
				2359: 2 ports FE 100 Gbit/s ROCE I/O module
				2360: 4 ports FE 10 Gbit/s ETH I/O module
				2361: 4 ports SO 25 Gbit/s RDMA I/O module
				2362: 2 ports SO 100 Gbit/s RDMA I/O module
				2363: 2 ports SO 100 Gbit/s RDMA I/O module
				4133: System Management Module
				4134: System Management Module
				4294967295: unknown"
			::= { hwInfoInterfaceModuleEntry 5 }
		
		-- 1.3.6.1.4.1.34774.4.1.23.5.13.1.6
		hwInfoInterfaceModuleLogicVersion OBJECT-TYPE
			SYNTAX OCTET STRING
			MAX-ACCESS read-only
			STATUS current
			DESCRIPTION
				"Logical version of an interface module, When the value is "--", indicates unknown."
			::= { hwInfoInterfaceModuleEntry 6 }
		
		-- 1.3.6.1.4.1.34774.4.1.23.5.13.1.7
		hwInfoInterfaceModulePCBVersion OBJECT-TYPE
			SYNTAX OCTET STRING
			MAX-ACCESS read-only
			STATUS current
			DESCRIPTION
				"PCB version of an interface module."
			::= { hwInfoInterfaceModuleEntry 7 }
		
		-- 1.3.6.1.4.1.34774.4.1.23.5.13.1.8
		hwInfoInterfaceModuleElectronicLabel OBJECT-TYPE
			SYNTAX OCTET STRING
			MAX-ACCESS read-only
			STATUS current
			DESCRIPTION
				"Electronic label of an interface module."
			::= { hwInfoInterfaceModuleEntry 8 }
		
		-- 1.3.6.1.4.1.34774.4.1.23.5.14
		hwInfoExpBoardTable OBJECT-TYPE
			SYNTAX SEQUENCE OF HwInfoExpBoardEntry
			MAX-ACCESS not-accessible
			STATUS current
			DESCRIPTION
				"This table is used to check the expansion module information about a device."
			::= { hwHardwareInfo 14 }
		
		-- 1.3.6.1.4.1.34774.4.1.23.5.14.1
		hwInfoExpBoardEntry OBJECT-TYPE
			SYNTAX HwInfoExpBoardEntry
			MAX-ACCESS not-accessible
			STATUS current
			DESCRIPTION
				"A table containing the part component."
			INDEX { hwInfoExpBoardID }
			::= { hwInfoExpBoardTable 1 }
		
		HwInfoExpBoardEntry ::=
			SEQUENCE { 
				hwInfoExpBoardID
					OCTET STRING,
				hwInfoExpBoardLocation
					OCTET STRING,
				hwInfoExpBoardHealthStatus
					Unsigned32,
				hwInfoExpBoardRunningStatus
					Unsigned32,
				hwInfoExpBoardModel
					Unsigned32,
				hwInfoExpBoardLogicVersion
					OCTET STRING,
				hwInfoExpBoardPCBVersion
					OCTET STRING,
				hwInfoExpBoardSESVersion
					OCTET STRING,
				hwInfoExpBoardELabel
					OCTET STRING
			 }

		-- 1.3.6.1.4.1.34774.4.1.23.5.14.1.1
		hwInfoExpBoardID OBJECT-TYPE
			SYNTAX OCTET STRING
			MAX-ACCESS read-only
			STATUS current
			DESCRIPTION
				"ID of an expansion module, table index."
			::= { hwInfoExpBoardEntry 1 }
		
		-- 1.3.6.1.4.1.34774.4.1.23.5.14.1.2
		hwInfoExpBoardLocation OBJECT-TYPE
			SYNTAX OCTET STRING
			MAX-ACCESS read-only
			STATUS current
			DESCRIPTION
				"Location of an expansion module."
			::= { hwInfoExpBoardEntry 2 }
		
		-- 1.3.6.1.4.1.34774.4.1.23.5.14.1.3
		hwInfoExpBoardHealthStatus OBJECT-TYPE
			SYNTAX Unsigned32
			MAX-ACCESS read-only
			STATUS current
			DESCRIPTION
				"Health status of an expansion module. For details, see:
				1 Normal
				2 Fault
				3 Pre-Fail
				4 Partially Broken
				5 Degraded
				6 Bad Sectors Found
				7 Bit Errors Found
				8 Consistent
				9 Inconsistent
				10 Busy
				11 No Input
				12 Low Battery
				13 Single Link Fault
				14 Invalid
				15 Write Protect
				16 single link
				17 No Redundant Link
				18 Offline"
			::= { hwInfoExpBoardEntry 3 }
		
		-- 1.3.6.1.4.1.34774.4.1.23.5.14.1.4
		hwInfoExpBoardRunningStatus OBJECT-TYPE
			SYNTAX Unsigned32
			MAX-ACCESS read-only
			STATUS current
			DESCRIPTION
				"Operating status of an expansion module. For details, see:
				1: Normal
				2: Running
				3: Not running
				4: Not existed
				5: Sleep in high temperature
				6: Starting
				7: Power failure rotection
				8: Spin down
				9: Started
				10: Link Up
				11: Link Down
				12: Powering on
				13: Powered off
				14: Pre-copy
				15: Copyback
				16: Reconstruction
				17: Expansion
				18: Unformatted
				19: Formatting
				20: Unmapped
				21: Initial synchronizing
				22: Consistent
				23: Synchronizing
				24: Synchronized
				25: Unsynchronized
				26: Split
				27: Online
				28: Offline
				29: Locked
				30: Enabled
				31: Disabled
				32: Balancing
				33: To be recovered
				34: Interrupted
				35: Invalid
				36: Not start
				37: Queuing
				38: Stopped
				39: Copying
				40: Completed
				41: Paused
				42: Reverse synchronizing
				43: Activated
				44: Restore
				45: Inactive
				46: Idle
				47: Powering off
				48: Charging
				49: Charging completed
				50: Discharging
				51: Upgrading
				52: Power Lost
				53: Initializing
				54: Apply change
				55: Online disable
				56: Offline disable
				57: Online frozen
				58: Offline frozen
				59: Closed
				60: Removing
				61: In service
				62: Out of service
				63: Running normal
				64: Running fail
				65: Running success
				66: Running success
				67: Running failed
				68: Waiting
				69: Canceling
				70: Canceled
				71: About to synchronize
				72: Synchronizing data
				73: Failed to synchronize
				74: Fault
				75: Migrating
				76: Migrated
				77: Activating
				78: Deactivating
				79: Start failed
				80: Stop failed
				81: Decommissioning
				82: Decommissioned
				83: Recommissioning
				84: Replacing node
				85: Scheduling
				86: Pausing
				87: Suspending
				88: Suspended
				89: Overload
				90: To be switch
				91: Switching
				92: To be cleanup
				93: Forced start
				94: Error
				95: Job completed
				96: Partition Migrating
				97: Mount
				98: Umount
				99: INSTALLING
				100: To Be Synchronized
				101: Connecting
				102: Service Switching
				103: Power-on failed
				104: REPAIRING
				105: abnormal
				106: Deleting
				107: Modifying
				108: Running(clearing data)
				109: Running(synchronizing data)
				110: Standby
				111: STOPPING
				112: RESTORE FAULT
				113: Cut Over
				114: Erasing
				115: Verifying
				119: Creating"
			::= { hwInfoExpBoardEntry 4 }
		
		-- 1.3.6.1.4.1.34774.4.1.23.5.14.1.5
		hwInfoExpBoardModel OBJECT-TYPE
			SYNTAX Unsigned32
			MAX-ACCESS read-only
			STATUS current
			DESCRIPTION
				"Model of an expansion module. Possible values are:
				0: SAS
				1: FC"
			::= { hwInfoExpBoardEntry 5 }
		
		-- 1.3.6.1.4.1.34774.4.1.23.5.14.1.6
		hwInfoExpBoardLogicVersion OBJECT-TYPE
			SYNTAX OCTET STRING
			MAX-ACCESS read-only
			STATUS current
			DESCRIPTION
				"Logical version of an expansion module, When the value is "--", indicates unknown."
			::= { hwInfoExpBoardEntry 6 }
		
		-- 1.3.6.1.4.1.34774.4.1.23.5.14.1.7
		hwInfoExpBoardPCBVersion OBJECT-TYPE
			SYNTAX OCTET STRING
			MAX-ACCESS read-only
			STATUS current
			DESCRIPTION
				"PCB version of an expansion module."
			::= { hwInfoExpBoardEntry 7 }
		
		-- 1.3.6.1.4.1.34774.4.1.23.5.14.1.8
		hwInfoExpBoardSESVersion OBJECT-TYPE
			SYNTAX OCTET STRING
			MAX-ACCESS read-only
			STATUS current
			DESCRIPTION
				"SES version of an expansion module."
			::= { hwInfoExpBoardEntry 8 }
		
		-- 1.3.6.1.4.1.34774.4.1.23.5.14.1.9
		hwInfoExpBoardELabel OBJECT-TYPE
			SYNTAX OCTET STRING
			MAX-ACCESS read-only
			STATUS current
			DESCRIPTION
				"Electronic label of an expansion module."
			::= { hwInfoExpBoardEntry 9 }
		
		-- 1.6
		isoConformance OBJECT IDENTIFIER ::= { iso 6 }
		
		-- 1.6.1
		isoGroups OBJECT IDENTIFIER ::= { isoConformance 1 }
		
		-- 1.6.1.1
		currentObjectGroup OBJECT-GROUP
			OBJECTS { hwInfoPortComID, hwInfoPortComLocation, hwInfoPortComHealthStatus, hwInfoPortComRunningStatus, hwInfoPortComType, 
				hwInfoPortEthID, hwInfoPortEthLocation, hwInfoPortEthHealthStatus, hwInfoPortEthRunningStatus, hwInfoPortEthType, 
				hwInfoPortEthIPv4Address, hwInfoPortEthSubnetMask, hwInfoPortEthIPv4Gateway, hwInfoPortEthIPv6Address, hwInfoPortEthIPv6PrefixLength, 
				hwInfoPortEthIPv6Gateway, hwInfoPortEthMAC, hwInfoPortEthRole, hwInfoPortEthMode, hwInfoPortEthMTU, 
				hwInfoPortEthWorkingRate, hwInfoPortEthBondName, hwInfoPortEthiSCSIPort, hwInfoPortEthiSCSIName, hwInfoPortEthErrorPackets, 
				hwInfoPortEthLostPackages, hwInfoPortFCID, hwInfoPortFCLocation, hwInfoPortFCHealthStatus, hwInfoPortFCRunningStatus, 
				hwInfoPortFCType, hwInfoPortFCWorkingRate, hwInfoPortFCConfiguredSpeed, hwInfoPortFCWWN, hwInfoPortFCRole, 
				hwInfoPortFCSFPStatus, hwInfoPortFCWorkingMode, hwInfoPortFCConfiguredMode, hwInfoPortFCFloginDelayTimes, hwInfoPortFCLostSignals, 
				hwInfoPortFCLinkErrorsCodes, hwInfoPortFCLostSynchronizations, hwInfoPortFCFailedConnections, hwInfoPortPCIEID, hwInfoPortPCIELocation, 
				hwInfoPortPCIEHealthStatus, hwInfoPortPCIERunningStatus, hwInfoPortPCIESpeed, hwInfoPortPCIECurrentPeerPortID, hwInfoPortPCIESuggestPeerPortID, 
				hwInfoPortPCIELostSignals, hwInfoPortPCIEECRCError, hwInfoPortPCIEBadTlp, hwInfoPortPCIERecvError, hwInfoPortPCIEChipEccError, 
				hwInfoPortSASID, hwInfoPortSASLocation, hwInfoPortSASHealthStatus, hwInfoPortSASRunningStatus, hwInfoPortSASType, 
				hwInfoPortSASWorkingRate, hwInfoPortSASWWN, hwInfoPortSASRole, hwInfoPortSASInvalidDword, hwInfoPortSASConsistErrors, 
				hwInfoPortSASLossOfDword, hwInfoPortSASPHYResetErrors, hwInfoPortSASStartTime, hwInfoPortSASEnabled, hwInfoInterfaceModuleID, 
				hwInfoInterfaceModuleLocation, hwInfoInterfaceModuleHealthStatus, hwInfoInterfaceModuleRunningStatus, hwInfoInterfaceModuleModel, hwInfoInterfaceModuleLogicVersion, 
				hwInfoInterfaceModulePCBVersion, hwInfoInterfaceModuleElectronicLabel, hwInfoDiskID, hwInfoDiskHealthStatus, hwInfoDiskRunningStatus, 
				hwInfoDiskType, hwInfoDiskCapacity, hwInfoDiskRole, hwInfoDiskSpeed, hwInfoDiskInterfaceBandwidth, 
				hwInfoDiskSectorSize, hwInfoDiskTemperature, hwInfoDiskModel, hwInfoDiskFirmwareVersion, hwInfoDiskManufacturer, 
				hwInfoDiskSerialNumber, hwInfoDiskLightStatus, hwInfoDiskDiskDomainID, hwInfoDiskDiskDomainName, hwInfoDiskDiskDomainTierID, 
				hwInfoDiskCofferDisk, hwInfoDiskRunTime, hwInfoDiskProgress, hwInfoDiskBarCode, hwInfoDiskCapacityUsage, 
				hwInfoDiskHealthMark, hwInfoDiskElectronicLabel, hwInfoControllerHealthStatus, hwInfoControllerRunningStatus, hwInfoControllerCPU, hwInfoControllerRole, 
				hwInfoControllerCacheCapacity, hwInfoControllerCPUUsage, hwInfoControllerMemoryUsage, hwInfoControllerVoltage, hwInfoControllerSoftwareVersion, 
				hwInfoControllerPCBVersion, hwInfoControllerSESVersion, hwInfoControllerBMCVersion, hwInfoControllerLogicVersion, hwInfoControllerBIOSVersion, 
				hwInfoControllerElectronicLabel, hwInfoPowerHealthStatus, hwInfoPowerRunningStatus, hwInfoPowerManufacturer, hwInfoPowerProduceDate, 
				hwInfoPowerSerialNumber, hwInfoFanHealthStatus, hwInfoFanElectronicLabel, hwInfoBBUHealthStatus, hwInfoBBURunningStatus, 
				hwInfoBBUType, hwInfoBBUNumberOfDischarges, hwInfoBBUFirmwareVersion, hwInfoBBUDeliveredOn, hwInfoBBUOwningController, 
				hwInfoBBUElectronicLabel, hwInfoEnclosureID, hwInfoEnclosureLogicType, hwInfoEnclosureHealthStatus, hwInfoEnclosureRunningStatus, 
				hwInfoEnclosureLocation, hwInfoEnclosureType, hwInfoEnclosureTemperature, hwInfoEnclosureSN, hwInfoEnclosureMAC, 
				hwInfoEnclosureHeight, hwInfoEnclosureExpansionDepth, hwInfoFanRunningStatus, hwInfoFanRunningLevel, hwInfoPowerModle, 
				hwInfoPowerVersion, hwInfoControllerID, hwInfoPowerID, hwInfoPowerType, hwInfoBBUID, 
				hwInfoControllerLocation, hwInfoDiskLocation, hwInfoEnclosureName, hwInfoEnclosureElectronicLabel, hwInfoPowerLocation, 
				hwInfoFanLocation, hwInfoBBULocation, hwInfoPortFCStartTime, hwInfoPortEthStartTime, hwInfoPortPCIEStartTime, 
				hwInfoExpBoardID, hwInfoExpBoardLocation, hwInfoExpBoardHealthStatus, hwInfoExpBoardRunningStatus, hwInfoExpBoardModel, 
				hwInfoExpBoardLogicVersion, hwInfoExpBoardPCBVersion, hwInfoExpBoardSESVersion, hwInfoExpBoardELabel, hwInfoBBUCurrentVoltage, 
				hwInfoFanID, hwInfoPortPCIEBadDllp }
			STATUS current
			DESCRIPTION 
				"Enter the description of the created OBJECT-GROUP."
			::= { isoGroups 1 }
		
		-- 1.6.2
		isoCompliances OBJECT IDENTIFIER ::= { isoConformance 2 }
		
--   this module
-- this module
		-- 1.6.2.1
		basicCompliance MODULE-COMPLIANCE
			STATUS current
			DESCRIPTION 
				"Enter the description of the created MODULE-COMPLIANCE."
			MODULE -- this module
				MANDATORY-GROUPS { currentObjectGroup }
			::= { isoCompliances 1 }
		
	
	END

--
-- HUAWEI-STORAGE-HARDWARE-MIB.mib
--
