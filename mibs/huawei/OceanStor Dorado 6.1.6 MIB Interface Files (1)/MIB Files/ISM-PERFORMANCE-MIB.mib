--
-- ISM-PERFORMANCE-MIB.mib
-- MIB generated by MG-SOFT Visual MIB Builder Version 6.0  Build 88
-- Friday, March 02, 2018 at 14:55:16
--

--  ISM-PERFORMANCE-MIB.mib
-- MIB generated by MG-SOFT Visual MIB Builder Version 4.0 Build 347
-- Friday, January 19, 2018 at 18:34:04
-- 
--  ISM-PERFORMANCE-MIB.mib
-- MIB generated by MG-SOFT Visual MIB Builder Version 4.0 Build 347
-- Thursday, March 27, 2014 at 11:42:32
-- 

	ISM-PERFORMANCE-MIB DEFINITIONS ::= BEGIN
 
		IMPORTS
			OBJECT-GROUP, MODULE-COMPLIANCE			
				FROM SNMPv2-CONF			
			enterprises, Integer32, Unsigned32, Counter64, 
			OBJECT-TYPE, MODULE-IDENTITY			
				FROM SNMPv2-SMI			
			TEXTUAL-CONVENTION			
				FROM SNMPv2-TC;
	
	
		-- 1.3.6.1.4.1.34774.4
		hwStorage MODULE-IDENTITY 
			LAST-UPDATED "201501011239Z"		-- January 01, 2015 at 12:39 GMT
			ORGANIZATION 
				"Huawei Technologies Co.,Ltd."
			CONTACT-INFO 
				"Huawei Industrial Base
				Bantian, Longgang
				Shenzhen 518129
				People's Republic of China
				Website: http://www.huawei.com
				Email: support@huawei.com"
			DESCRIPTION 
				"The ISM-PERFORMANCE-MIB contains objects to query preformance information."
			REVISION "201304071716Z"		-- April 07, 2013 at 17:16 GMT
			DESCRIPTION 
				"Description."
			::= { huaweistorage 4 }

		
	
--
-- Textual conventions
--
	
--  January 01, 2015 at 12:39 GMT
-- April 07, 2013 at 17:16 GMT
-- 
-- Textual conventions
-- 
--  January 01, 2015 at 12:39 GMT
-- April 07, 2013 at 17:16 GMT
-- 
-- Textual conventions
-- 
		NodeCodeString ::= TEXTUAL-CONVENTION
			DISPLAY-HINT 
				"255a"
			STATUS current
			DESCRIPTION 
				"characters in length."
			SYNTAX OCTET STRING (SIZE (15..17))

	
--
-- Node definitions
--
	
--  Node definitions
-- 
-- Node definitions
-- 
		-- 1.3.6.1.4.1.34774
		huaweistorage OBJECT IDENTIFIER ::= { enterprises 34774 }

		
		-- 1.3.6.1.4.1.34774.4.1
		hwISM OBJECT IDENTIFIER ::= { hwStorage 1 }

		
		-- 1.3.6.1.4.1.34774.4.1.21
		hwPerformance OBJECT IDENTIFIER ::= { hwISM 21 }

		
		-- 1.3.6.1.4.1.34774.4.1.21.1
		hwPerformanceSwitch OBJECT-TYPE
			SYNTAX Integer32 (0..1)
			MAX-ACCESS read-write
			STATUS current
			DESCRIPTION
				"Performance statistics switch. The value can be:
				0: Disabled
				1: Enabled"
			::= { hwPerformance 1 }

		
		-- 1.3.6.1.4.1.34774.4.1.21.3
		hwPerfNodeTable OBJECT-TYPE
			SYNTAX SEQUENCE OF HwPerfNodeEntry
			MAX-ACCESS not-accessible
			STATUS current
			DESCRIPTION
				"This table is used to query the performance data of nodes."
			::= { hwPerformance 3 }

		
		-- 1.3.6.1.4.1.34774.4.1.21.3.1
		hwPerfNodeEntry OBJECT-TYPE
			SYNTAX HwPerfNodeEntry
			MAX-ACCESS not-accessible
			STATUS current
			DESCRIPTION
				"A table containing the part component."
			INDEX { hwPerfNodeIfIndex }
			::= { hwPerfNodeTable 1 }

		
		HwPerfNodeEntry ::=
			SEQUENCE { 
				hwPerfNodeIfIndex
					Unsigned32,
				hwPerfNodeCPUUsage
					Unsigned32,
				hwPerfNodeAvgCacheUsage
					Unsigned32,
				hwPerfNodeDelay
					Unsigned32,
				hwPerfNodeTotalIOPS
					Unsigned32,
				hwPerfNodeReadIOPS
					Unsigned32,
				hwPerfNodeWriteIOPS
					Unsigned32,
				hwPerfNodeTotalTraffic
					Unsigned32,
				hwPerfNodeReadTraffic
					Unsigned32,
				hwPerfNodeWriteTraffic
					Unsigned32,
				hwPerfNodeFileBandwidth
					Counter64,
				hwPerfNodeFileOPS
					Counter64
			 }

		-- 1.3.6.1.4.1.34774.4.1.21.3.1.1
		hwPerfNodeIfIndex OBJECT-TYPE
			SYNTAX Unsigned32
			MAX-ACCESS read-only
			STATUS current
			DESCRIPTION
				"Controller node ID.
				Controller node ID = Controller enclosure ID x Number of controllers in the controller enclosure + Controller ID. In controller name 1A, 1 indicates the controller enclosure ID and A indicates the controller ID (A, B, C, D correspond to 0, 1, 2, 3, respectively). If a controller enclosure has two controllers, the node ID is 2. If a controller enclosure has four controllers, the node ID is 4."
			::= { hwPerfNodeEntry 1 }

		
		-- 1.3.6.1.4.1.34774.4.1.21.3.1.2
		hwPerfNodeCPUUsage OBJECT-TYPE
			SYNTAX Unsigned32
			MAX-ACCESS read-only
			STATUS current
			DESCRIPTION
				"CPU usage of the node (unit: %)."
			::= { hwPerfNodeEntry 2 }

		
		-- 1.3.6.1.4.1.34774.4.1.21.3.1.3
		hwPerfNodeAvgCacheUsage OBJECT-TYPE
			SYNTAX Unsigned32
			MAX-ACCESS read-only
			STATUS current
			DESCRIPTION
				"Average cache usage of the node (unit: %)."
			::= { hwPerfNodeEntry 3 }

		
		-- 1.3.6.1.4.1.34774.4.1.21.3.1.4
		hwPerfNodeDelay OBJECT-TYPE
			SYNTAX Unsigned32
			MAX-ACCESS read-only
			STATUS current
			DESCRIPTION
				"Average I/O latency of the node (unit: ms)."
			::= { hwPerfNodeEntry 4 }

		
		-- 1.3.6.1.4.1.34774.4.1.21.3.1.5
		hwPerfNodeTotalIOPS OBJECT-TYPE
			SYNTAX Unsigned32
			MAX-ACCESS read-only
			STATUS current
			DESCRIPTION
				"Total IOPS of the node (unit: IO/s)."
			::= { hwPerfNodeEntry 5 }

		
		-- 1.3.6.1.4.1.34774.4.1.21.3.1.6
		hwPerfNodeReadIOPS OBJECT-TYPE
			SYNTAX Unsigned32
			MAX-ACCESS read-only
			STATUS current
			DESCRIPTION
				"Read IOPS of the node (unit: IO/s)."
			::= { hwPerfNodeEntry 6 }

		
		-- 1.3.6.1.4.1.34774.4.1.21.3.1.7
		hwPerfNodeWriteIOPS OBJECT-TYPE
			SYNTAX Unsigned32
			MAX-ACCESS read-only
			STATUS current
			DESCRIPTION
				"Write IOPS of the node (unit: IO/s)."
			::= { hwPerfNodeEntry 7 }

		
		-- 1.3.6.1.4.1.34774.4.1.21.3.1.8
		hwPerfNodeTotalTraffic OBJECT-TYPE
			SYNTAX Unsigned32
			MAX-ACCESS read-only
			STATUS current
			DESCRIPTION
				"Total bandwidth for the node (unit: MB/s)."
			::= { hwPerfNodeEntry 8 }

		
		-- 1.3.6.1.4.1.34774.4.1.21.3.1.9
		hwPerfNodeReadTraffic OBJECT-TYPE
			SYNTAX Unsigned32
			MAX-ACCESS read-only
			STATUS current
			DESCRIPTION
				"Read bandwidth for the node (unit: MB/s)."
			::= { hwPerfNodeEntry 9 }

		
		-- 1.3.6.1.4.1.34774.4.1.21.3.1.10
		hwPerfNodeWriteTraffic OBJECT-TYPE
			SYNTAX Unsigned32
			MAX-ACCESS read-only
			STATUS current
			DESCRIPTION
				"Write bandwidth for the node (unit: MB/s)."
			::= { hwPerfNodeEntry 10 }

		
		-- 1.3.6.1.4.1.34774.4.1.21.3.1.11
		hwPerfNodeFileBandwidth OBJECT-TYPE
			SYNTAX Counter64
			MAX-ACCESS read-only
			STATUS current
			DESCRIPTION
				"Node file bandwidth (unit: byte/s)."
			::= { hwPerfNodeEntry 11 }

		
		-- 1.3.6.1.4.1.34774.4.1.21.3.1.12
		hwPerfNodeFileOPS OBJECT-TYPE
			SYNTAX Counter64
			MAX-ACCESS read-only
			STATUS current
			DESCRIPTION
				"Node file OPS"
			::= { hwPerfNodeEntry 12 }

		
		-- 1.3.6.1.4.1.34774.4.1.21.4
		hwPerfLunTable OBJECT-TYPE
			SYNTAX SEQUENCE OF HwPerfLunEntry
			MAX-ACCESS not-accessible
			STATUS current
			DESCRIPTION
				"This table is used to query the performance data (skip the grayed texts) of LUNs."
			::= { hwPerformance 4 }

		
		-- 1.3.6.1.4.1.34774.4.1.21.4.1
		hwPerfLunEntry OBJECT-TYPE
			SYNTAX HwPerfLunEntry
			MAX-ACCESS not-accessible
			STATUS current
			DESCRIPTION
				"A table containing the part component."
			INDEX { hwPerfLunID }
			::= { hwPerfLunTable 1 }

		
		HwPerfLunEntry ::=
			SEQUENCE { 
				hwPerfLunID
					Unsigned32,
				hwPerfLunHitRate
					Unsigned32,
				hwPerfLunTotalIOPS
					Unsigned32,
				hwPerfLunReadIOPS
					Unsigned32,
				hwPerfLunWriteIOPS
					Unsigned32,
				hwPerfLunTotalTraffic
					Unsigned32,
				hwPerfLunReadTraffic
					Unsigned32,
				hwPerfLunWriteTraffic
					Unsigned32,
				hwPerfLunReadIORate
					Unsigned32,
				hwPerfLunWriteIORate
					Unsigned32,
				hwPerfLunMaxTraffic
					Unsigned32,
				hwPerfLunMaxIOPS
					Unsigned32,
				hwPerfLunAverageIOResponseTime
					Unsigned32,
				hwPerfLunMaxIOResponseTime
					Unsigned32,
				hwPerfLunAverageReadIOLatency
					Unsigned32,
				hwPerfLunAverageWriteIOLatency
					Unsigned32
			 }

		-- 1.3.6.1.4.1.34774.4.1.21.4.1.1
		hwPerfLunID OBJECT-TYPE
			SYNTAX Unsigned32
			MAX-ACCESS read-only
			STATUS current
			DESCRIPTION
				"LUN ID."
			::= { hwPerfLunEntry 1 }

		
		-- 1.3.6.1.4.1.34774.4.1.21.4.1.2
		hwPerfLunHitRate OBJECT-TYPE
			SYNTAX Unsigned32
			MAX-ACCESS read-only
			STATUS current
			DESCRIPTION
				"I/O hit ratio of the LUN (unit: IO/s)."
			::= { hwPerfLunEntry 2 }

		
		-- 1.3.6.1.4.1.34774.4.1.21.4.1.3
		hwPerfLunTotalIOPS OBJECT-TYPE
			SYNTAX Unsigned32
			MAX-ACCESS read-only
			STATUS current
			DESCRIPTION
				"Current IOPS of the LUN (unit: IO/s)."
			::= { hwPerfLunEntry 3 }

		
		-- 1.3.6.1.4.1.34774.4.1.21.4.1.4
		hwPerfLunReadIOPS OBJECT-TYPE
			SYNTAX Unsigned32
			MAX-ACCESS read-only
			STATUS current
			DESCRIPTION
				"Current read IOPS of the LUN (unit: IO/s)."
			::= { hwPerfLunEntry 4 }

		
		-- 1.3.6.1.4.1.34774.4.1.21.4.1.5
		hwPerfLunWriteIOPS OBJECT-TYPE
			SYNTAX Unsigned32
			MAX-ACCESS read-only
			STATUS current
			DESCRIPTION
				"Current write IOPS of the LUN (unit: IO/s)."
			::= { hwPerfLunEntry 5 }

		
		-- 1.3.6.1.4.1.34774.4.1.21.4.1.6
		hwPerfLunTotalTraffic OBJECT-TYPE
			SYNTAX Unsigned32
			MAX-ACCESS read-only
			STATUS current
			DESCRIPTION
				"Current total bandwidth for the LUN (unit: MB/s)."
			::= { hwPerfLunEntry 6 }

		
		-- 1.3.6.1.4.1.34774.4.1.21.4.1.7
		hwPerfLunReadTraffic OBJECT-TYPE
			SYNTAX Unsigned32
			MAX-ACCESS read-only
			STATUS current
			DESCRIPTION
				"Current read bandwidth for the LUN (unit: MB/s)."
			::= { hwPerfLunEntry 7 }

		
		-- 1.3.6.1.4.1.34774.4.1.21.4.1.8
		hwPerfLunWriteTraffic OBJECT-TYPE
			SYNTAX Unsigned32
			MAX-ACCESS read-only
			STATUS current
			DESCRIPTION
				"Current write bandwidth for the LUN (unit: MB/s)."
			::= { hwPerfLunEntry 8 }

		
		-- 1.3.6.1.4.1.34774.4.1.21.4.1.9
		hwPerfLunReadIORate OBJECT-TYPE
			SYNTAX Unsigned32
			MAX-ACCESS read-only
			STATUS current
			DESCRIPTION
				"Read I/O ratio of the LUN (unit: IO/s)."
			::= { hwPerfLunEntry 9 }

		
		-- 1.3.6.1.4.1.34774.4.1.21.4.1.10
		hwPerfLunWriteIORate OBJECT-TYPE
			SYNTAX Unsigned32
			MAX-ACCESS read-only
			STATUS current
			DESCRIPTION
				"Write I/O ratio of the LUN (unit: IO/s)."
			::= { hwPerfLunEntry 10 }

		
		-- 1.3.6.1.4.1.34774.4.1.21.4.1.11
		hwPerfLunMaxTraffic OBJECT-TYPE
			SYNTAX Unsigned32
			MAX-ACCESS read-only
			STATUS current
			DESCRIPTION
				"Maximum bandwidth for the LUN (unit: MB/s)."
			::= { hwPerfLunEntry 11 }

		
		-- 1.3.6.1.4.1.34774.4.1.21.4.1.12
		hwPerfLunMaxIOPS OBJECT-TYPE
			SYNTAX Unsigned32
			MAX-ACCESS read-only
			STATUS current
			DESCRIPTION
				"Maximum IOPS of the LUN (unit: IO/s)."
			::= { hwPerfLunEntry 12 }

		
		-- 1.3.6.1.4.1.34774.4.1.21.4.1.13
		hwPerfLunAverageIOResponseTime OBJECT-TYPE
			SYNTAX Unsigned32
			MAX-ACCESS read-only
			STATUS current
			DESCRIPTION
				"Average IO response time (unit:us)."
			::= { hwPerfLunEntry 13 }

 
		-- 1.3.6.1.4.1.34774.4.1.21.4.1.14
		hwPerfLunMaxIOResponseTime OBJECT-TYPE
			SYNTAX Unsigned32
			MAX-ACCESS read-only
			STATUS current
			DESCRIPTION
				"Maximum IO response time (unit:us)."
			::= { hwPerfLunEntry 14 }

		
 
		-- 1.3.6.1.4.1.34774.4.1.21.4.1.15
		hwPerfLunAverageReadIOLatency OBJECT-TYPE
			SYNTAX Unsigned32
			MAX-ACCESS read-only
			STATUS current
			DESCRIPTION
				"Average read IO response time (unit:us)."
			::= { hwPerfLunEntry 15 }

		
 
		-- 1.3.6.1.4.1.34774.4.1.21.4.1.16
		hwPerfLunAverageWriteIOLatency OBJECT-TYPE
			SYNTAX Unsigned32
			MAX-ACCESS read-only
			STATUS current
			DESCRIPTION
				"Average write IO response time (unit:us)."
			::= { hwPerfLunEntry 16 }

		
		-- 1.3.6.1.4.1.34774.4.1.21.5
		hwPerfPortTable OBJECT-TYPE
			SYNTAX SEQUENCE OF HwPerfPortEntry
			MAX-ACCESS not-accessible
			STATUS current
			DESCRIPTION
				"This table is used to query the performance data of ETH, FC, FCoE, Bond ports."
			::= { hwPerformance 5 }

		
		-- 1.3.6.1.4.1.34774.4.1.21.5.1
		hwPerfPortEntry OBJECT-TYPE
			SYNTAX HwPerfPortEntry
			MAX-ACCESS not-accessible
			STATUS current
			DESCRIPTION
				"A table containing the part component."
			INDEX { hwPerfPortIfIndex }
			::= { hwPerfPortTable 1 }

		
		HwPerfPortEntry ::=
			SEQUENCE { 
				hwPerfPortIfIndex
					Unsigned32,
				hwPerfPortDelay
					Unsigned32,
				hwPerfPortTotalIOPS
					Unsigned32,
				hwPerfPortReadIOPS
					Unsigned32,
				hwPerfPortWriteIOPS
					Unsigned32,
				hwPerfPortTotalTraffic
					Unsigned32,
				hwPerfPortReadTraffic
					Unsigned32,
				hwPerfPortWriteTraffic
					Unsigned32,
				hwPerfPortMaxTraffic
					Unsigned32,
				hwPerfPortMaxIOPS
					Unsigned32,
				hwPerfPortLocation
					OCTET STRING
			 }

		-- 1.3.6.1.4.1.34774.4.1.21.5.1.1
		hwPerfPortIfIndex OBJECT-TYPE
			SYNTAX Unsigned32
			MAX-ACCESS read-only
			STATUS current
			DESCRIPTION
				"Index to the port."
			::= { hwPerfPortEntry 1 }

		
		-- 1.3.6.1.4.1.34774.4.1.21.5.1.2
		hwPerfPortDelay OBJECT-TYPE
			SYNTAX Unsigned32
			MAX-ACCESS read-only
			STATUS current
			DESCRIPTION
				"I/O latency of the port (unit: ms)."
			::= { hwPerfPortEntry 2 }

		
		-- 1.3.6.1.4.1.34774.4.1.21.5.1.3
		hwPerfPortTotalIOPS OBJECT-TYPE
			SYNTAX Unsigned32
			MAX-ACCESS read-only
			STATUS current
			DESCRIPTION
				"IOPS of the port (unit: IO/s)."
			::= { hwPerfPortEntry 3 }

		
		-- 1.3.6.1.4.1.34774.4.1.21.5.1.4
		hwPerfPortReadIOPS OBJECT-TYPE
			SYNTAX Unsigned32
			MAX-ACCESS read-only
			STATUS current
			DESCRIPTION
				"Read IOPS of the port (unit: IO/s)."
			::= { hwPerfPortEntry 4 }

		
		-- 1.3.6.1.4.1.34774.4.1.21.5.1.5
		hwPerfPortWriteIOPS OBJECT-TYPE
			SYNTAX Unsigned32
			MAX-ACCESS read-only
			STATUS current
			DESCRIPTION
				"Write IOPS of the port (unit: IO/s)."
			::= { hwPerfPortEntry 5 }

		
		-- 1.3.6.1.4.1.34774.4.1.21.5.1.6
		hwPerfPortTotalTraffic OBJECT-TYPE
			SYNTAX Unsigned32
			MAX-ACCESS read-only
			STATUS current
			DESCRIPTION
				"Total bandwidth for the port (unit: MB/s)."
			::= { hwPerfPortEntry 6 }

		
		-- 1.3.6.1.4.1.34774.4.1.21.5.1.7
		hwPerfPortReadTraffic OBJECT-TYPE
			SYNTAX Unsigned32
			MAX-ACCESS read-only
			STATUS current
			DESCRIPTION
				"Read bandwidth for the port (unit: MB/s)."
			::= { hwPerfPortEntry 7 }

		
		-- 1.3.6.1.4.1.34774.4.1.21.5.1.8
		hwPerfPortWriteTraffic OBJECT-TYPE
			SYNTAX Unsigned32
			MAX-ACCESS read-only
			STATUS current
			DESCRIPTION
				"Write bandwidth for the port (unit: MB/s)."
			::= { hwPerfPortEntry 8 }

		
		-- 1.3.6.1.4.1.34774.4.1.21.5.1.9
		hwPerfPortMaxTraffic OBJECT-TYPE
			SYNTAX Unsigned32
			MAX-ACCESS read-only
			STATUS current
			DESCRIPTION
				"Maximum bandwidth for the port (unit: MB/s)."
			::= { hwPerfPortEntry 9 }

		
		-- 1.3.6.1.4.1.34774.4.1.21.5.1.10
		hwPerfPortMaxIOPS OBJECT-TYPE
			SYNTAX Unsigned32
			MAX-ACCESS read-only
			STATUS current
			DESCRIPTION
				"Maximum IOPS of the port (unit: IO/s)."
			::= { hwPerfPortEntry 10 }

		
		-- 1.3.6.1.4.1.34774.4.1.21.5.1.11
		hwPerfPortLocation OBJECT-TYPE
			SYNTAX OCTET STRING
			MAX-ACCESS read-only
			STATUS current
			DESCRIPTION
				"Location of the port."
			::= { hwPerfPortEntry 11 }

		
		-- 1.3.6.1.4.1.34774.4.1.21.7
		hwPerfCacheTable OBJECT-TYPE
			SYNTAX SEQUENCE OF HwPerfCacheEntry
			MAX-ACCESS not-accessible
			STATUS current
			DESCRIPTION
				"This table is used to query the performance data of caches."
			::= { hwPerformance 7 }

		
		-- 1.3.6.1.4.1.34774.4.1.21.7.1
		hwPerfCacheEntry OBJECT-TYPE
			SYNTAX HwPerfCacheEntry
			MAX-ACCESS not-accessible
			STATUS current
			DESCRIPTION
				"A table containing the part component."
			INDEX { hwPerfCacheID }
			::= { hwPerfCacheTable 1 }

		
		HwPerfCacheEntry ::=
			SEQUENCE { 
				hwPerfCacheID
					Unsigned32,
				hwPerfCacheReadUtilization
					Integer32,
				hwPerfCacheWriteUtilization
					Integer32,
				hwPerfCacheMirrorWriteUtilization
					Integer32,
				hwPerfCacheHitRatio
					Integer32
			 }

		-- 1.3.6.1.4.1.34774.4.1.21.7.1.1
		hwPerfCacheID OBJECT-TYPE
			SYNTAX Unsigned32
			MAX-ACCESS read-only
			STATUS current
			DESCRIPTION
				"Controller node ID.
				 Controller node ID = Controller enclosure ID x Number of controllers in the controller enclosure + Controller ID. In controller name 1A, 1 indicates the controller enclosure ID and A indicates the controller ID (A, B, C, D correspond to 0, 1, 2, 3, respectively). If a controller enclosure has two controllers, the node ID is 2. If a controller enclosure has four controllers, the node ID is 4."
			::= { hwPerfCacheEntry 1 }

		
		-- 1.3.6.1.4.1.34774.4.1.21.7.1.2
		hwPerfCacheReadUtilization OBJECT-TYPE
			SYNTAX Integer32
			MAX-ACCESS read-only
			STATUS current
			DESCRIPTION
				"Cache read usage (unit: %)."
			::= { hwPerfCacheEntry 2 }

		
		-- 1.3.6.1.4.1.34774.4.1.21.7.1.3
		hwPerfCacheWriteUtilization OBJECT-TYPE
			SYNTAX Integer32
			MAX-ACCESS read-only
			STATUS current
			DESCRIPTION
				"Cache write usage (unit: %)."
			::= { hwPerfCacheEntry 3 }

		
		-- 1.3.6.1.4.1.34774.4.1.21.7.1.4
		hwPerfCacheMirrorWriteUtilization OBJECT-TYPE
			SYNTAX Integer32
			MAX-ACCESS read-only
			STATUS current
			DESCRIPTION
				"Cache mirror write usage (unit: %)."
			::= { hwPerfCacheEntry 4 }

		
		-- 1.3.6.1.4.1.34774.4.1.21.7.1.5
		hwPerfCacheHitRatio OBJECT-TYPE
			SYNTAX Integer32
			MAX-ACCESS read-only
			STATUS current
			DESCRIPTION
				"Cache hit ratio."
			::= { hwPerfCacheEntry 5 }

		
		-- 1.3.6.1.4.1.34774.4.1.21.10
		hwPerfControllerNFSV3Table OBJECT-TYPE
			SYNTAX SEQUENCE OF HwPerfControllerNFSV3Entry
			MAX-ACCESS not-accessible
			STATUS current
			DESCRIPTION
				"This table is used to query the NFSv3 performance data of controllers."
			::= { hwPerformance 10 }

		
		-- 1.3.6.1.4.1.34774.4.1.21.10.1
		hwPerfControllerNFSV3Entry OBJECT-TYPE
			SYNTAX HwPerfControllerNFSV3Entry
			MAX-ACCESS not-accessible
			STATUS current
			DESCRIPTION
				"A table containing the part component."
			INDEX { hwPerfControllerNFSV3ID }
			::= { hwPerfControllerNFSV3Table 1 }

		
		HwPerfControllerNFSV3Entry ::=
			SEQUENCE { 
				hwPerfControllerNFSV3ID
					OCTET STRING,
				hwPerfControllerNFSV3OPS
					Counter64,
				hwPerfControllerNFSV3Bps
					Counter64
			 }

		-- 1.3.6.1.4.1.34774.4.1.21.10.1.1
		hwPerfControllerNFSV3ID OBJECT-TYPE
			SYNTAX OCTET STRING
			MAX-ACCESS read-only
			STATUS current
			DESCRIPTION
				"Controller ID."
			::= { hwPerfControllerNFSV3Entry 1 }

		
		-- 1.3.6.1.4.1.34774.4.1.21.10.1.2
		hwPerfControllerNFSV3OPS OBJECT-TYPE
			SYNTAX Counter64
			MAX-ACCESS read-only
			STATUS current
			DESCRIPTION
				"NFSv3 OPS of the controller."
			::= { hwPerfControllerNFSV3Entry 2 }

		
		-- 1.3.6.1.4.1.34774.4.1.21.10.1.3
		hwPerfControllerNFSV3Bps OBJECT-TYPE
			SYNTAX Counter64
			MAX-ACCESS read-only
			STATUS current
			DESCRIPTION
				"NFSv3 throughput of the controller (unit: byte/s)."
			::= { hwPerfControllerNFSV3Entry 3 }

		
		-- 1.3.6.1.4.1.34774.4.1.21.11
		hwPerfControllerNFSV4Table OBJECT-TYPE
			SYNTAX SEQUENCE OF HwPerfControllerNFSV4Entry
			MAX-ACCESS not-accessible
			STATUS current
			DESCRIPTION
				"This table is used to query the NFSv4 performance data of controllers."
			::= { hwPerformance 11 }

		
		-- 1.3.6.1.4.1.34774.4.1.21.11.1
		hwPerfControllerNFSV4Entry OBJECT-TYPE
			SYNTAX HwPerfControllerNFSV4Entry
			MAX-ACCESS not-accessible
			STATUS current
			DESCRIPTION
				"A table containing the part component."
			INDEX { hwPerfControllerNFSV4ID }
			::= { hwPerfControllerNFSV4Table 1 }

		
		HwPerfControllerNFSV4Entry ::=
			SEQUENCE { 
				hwPerfControllerNFSV4ID
					OCTET STRING,
				hwPerfControllerNFSV4OPS
					Counter64,
				hwPerfControllerNFSV4Bps
					Counter64
			 }

		-- 1.3.6.1.4.1.34774.4.1.21.11.1.1
		hwPerfControllerNFSV4ID OBJECT-TYPE
			SYNTAX OCTET STRING
			MAX-ACCESS read-only
			STATUS current
			DESCRIPTION
				"Controller ID."
			::= { hwPerfControllerNFSV4Entry 1 }

		
		-- 1.3.6.1.4.1.34774.4.1.21.11.1.2
		hwPerfControllerNFSV4OPS OBJECT-TYPE
			SYNTAX Counter64
			MAX-ACCESS read-only
			STATUS current
			DESCRIPTION
				"NFSv4 OPS of the controller."
			::= { hwPerfControllerNFSV4Entry 2 }

		
		-- 1.3.6.1.4.1.34774.4.1.21.11.1.3
		hwPerfControllerNFSV4Bps OBJECT-TYPE
			SYNTAX Counter64
			MAX-ACCESS read-only
			STATUS current
			DESCRIPTION
				"NFSv4 throughput of the controller (unit: byte/s)."
			::= { hwPerfControllerNFSV4Entry 3 }

		
		-- 1.3.6.1.4.1.34774.4.1.21.12
		hwPerfControllerSMBV1Table OBJECT-TYPE
			SYNTAX SEQUENCE OF HwPerfControllerSMBV1Entry
			MAX-ACCESS not-accessible
			STATUS current
			DESCRIPTION
				"This table is used to query the SMB V1 performance data of controllers."
			::= { hwPerformance 12 }

		
		-- 1.3.6.1.4.1.34774.4.1.21.12.1
		hwPerfControllerSMBV1Entry OBJECT-TYPE
			SYNTAX HwPerfControllerSMBV1Entry
			MAX-ACCESS not-accessible
			STATUS current
			DESCRIPTION
				"A table containing the part component."
			INDEX { hwPerfControllerSMBV1ID }
			::= { hwPerfControllerSMBV1Table 1 }

		
		HwPerfControllerSMBV1Entry ::=
			SEQUENCE { 
				hwPerfControllerSMBV1ID
					OCTET STRING,
				hwPerfControllerSMBV1OPS
					Counter64,
				hwPerfControllerSMBV1Bps
					Counter64
			 }

		-- 1.3.6.1.4.1.34774.4.1.21.12.1.1
		hwPerfControllerSMBV1ID OBJECT-TYPE
			SYNTAX OCTET STRING
			MAX-ACCESS read-only
			STATUS current
			DESCRIPTION
				"Controller ID."
			::= { hwPerfControllerSMBV1Entry 1 }

		
		-- 1.3.6.1.4.1.34774.4.1.21.12.1.2
		hwPerfControllerSMBV1OPS OBJECT-TYPE
			SYNTAX Counter64
			MAX-ACCESS read-only
			STATUS current
			DESCRIPTION
				"SMB V1 OPS of the controller."
			::= { hwPerfControllerSMBV1Entry 2 }

		
		-- 1.3.6.1.4.1.34774.4.1.21.12.1.3
		hwPerfControllerSMBV1Bps OBJECT-TYPE
			SYNTAX Counter64
			MAX-ACCESS read-only
			STATUS current
			DESCRIPTION
				"SMB V1 throughput of the controller (unit: byte/s)."
			::= { hwPerfControllerSMBV1Entry 3 }

		
		-- 1.3.6.1.4.1.34774.4.1.21.13
		hwPerfControllerSMBV2Table OBJECT-TYPE
			SYNTAX SEQUENCE OF HwPerfControllerSMBV2Entry
			MAX-ACCESS not-accessible
			STATUS current
			DESCRIPTION
				"This table is used to query the SMB V2 performance data of controllers."
			::= { hwPerformance 13 }

		
		-- 1.3.6.1.4.1.34774.4.1.21.13.1
		hwPerfControllerSMBV2Entry OBJECT-TYPE
			SYNTAX HwPerfControllerSMBV2Entry
			MAX-ACCESS not-accessible
			STATUS current
			DESCRIPTION
				"A table containing the part component."
			INDEX { hwPerfControllerSMBV2ID }
			::= { hwPerfControllerSMBV2Table 1 }

		
		HwPerfControllerSMBV2Entry ::=
			SEQUENCE { 
				hwPerfControllerSMBV2ID
					OCTET STRING,
				hwPerfControllerSMBV2OPS
					Counter64,
				hwPerfControllerSMBV2Bps
					Counter64
			 }

		-- 1.3.6.1.4.1.34774.4.1.21.13.1.1
		hwPerfControllerSMBV2ID OBJECT-TYPE
			SYNTAX OCTET STRING
			MAX-ACCESS read-only
			STATUS current
			DESCRIPTION
				"Controller ID."
			::= { hwPerfControllerSMBV2Entry 1 }

		
		-- 1.3.6.1.4.1.34774.4.1.21.13.1.2
		hwPerfControllerSMBV2OPS OBJECT-TYPE
			SYNTAX Counter64
			MAX-ACCESS read-only
			STATUS current
			DESCRIPTION
				"SMB V2 OPS of the controller."
			::= { hwPerfControllerSMBV2Entry 2 }

		
		-- 1.3.6.1.4.1.34774.4.1.21.13.1.3
		hwPerfControllerSMBV2Bps OBJECT-TYPE
			SYNTAX Counter64
			MAX-ACCESS read-only
			STATUS current
			DESCRIPTION
				"SMB V2 throughput of the controller (unit: byte/s)."
			::= { hwPerfControllerSMBV2Entry 3 }

		
		-- 1.3.6.1.4.1.34774.4.1.21.14
		hwPerfFileSystemTable OBJECT-TYPE
			SYNTAX SEQUENCE OF HwPerfFileSystemEntry
			MAX-ACCESS not-accessible
			STATUS current
			DESCRIPTION
				"This table is used to query the performance data of a file system."
			::= { hwPerformance 14 }

		
		-- 1.3.6.1.4.1.34774.4.1.21.14.1
		hwPerfFileSystemEntry OBJECT-TYPE
			SYNTAX HwPerfFileSystemEntry
			MAX-ACCESS not-accessible
			STATUS current
			DESCRIPTION
				"A table containing the part component."
			INDEX { hwPerfFileSystemID }
			::= { hwPerfFileSystemTable 1 }

		
		HwPerfFileSystemEntry ::=
			SEQUENCE { 
				hwPerfFileSystemID
					OCTET STRING,
				hwPerfFileSystemOPS
					Counter64,
				hwPerfFileSystemServiceTime
					Counter64,
				hwPerfFileSystemReadOPS
					Counter64,
				hwPerfFileSystemReadBandwidth
					Counter64,
				hwPerfFileSystemAvRdOPSRspTime
					Counter64,
				hwPerfFileSystemAvWrOPSRspTime
					Counter64,
				hwPerfFileSystemWriteOPS
					Counter64,
				hwPerfFileSystemWriteBandwidth
					Counter64
			 }

		-- 1.3.6.1.4.1.34774.4.1.21.14.1.1
		hwPerfFileSystemID OBJECT-TYPE
			SYNTAX OCTET STRING
			MAX-ACCESS read-only
			STATUS current
			DESCRIPTION
				"File system ID."
			::= { hwPerfFileSystemEntry 1 }

		
		-- 1.3.6.1.4.1.34774.4.1.21.14.1.2
		hwPerfFileSystemOPS OBJECT-TYPE
			SYNTAX Counter64
			MAX-ACCESS read-only
			STATUS current
			DESCRIPTION
				"File system OPS."
			::= { hwPerfFileSystemEntry 2 }

		
		-- 1.3.6.1.4.1.34774.4.1.21.14.1.3
		hwPerfFileSystemServiceTime OBJECT-TYPE
			SYNTAX Counter64
			MAX-ACCESS read-only
			STATUS current
			DESCRIPTION
				"Service time of the file system (unit: μs)."
			::= { hwPerfFileSystemEntry 3 }

		
		-- 1.3.6.1.4.1.34774.4.1.21.14.1.4
		hwPerfFileSystemReadOPS OBJECT-TYPE
			SYNTAX Counter64
			MAX-ACCESS read-only
			STATUS current
			DESCRIPTION
				"Read OPS of the file system."
			::= { hwPerfFileSystemEntry 4 }

		
		-- 1.3.6.1.4.1.34774.4.1.21.14.1.5
		hwPerfFileSystemReadBandwidth OBJECT-TYPE
			SYNTAX Counter64
			MAX-ACCESS read-only
			STATUS current
			DESCRIPTION
				"Read bandwidth of the file system (unit: MB/s)."
			::= { hwPerfFileSystemEntry 5 }

		
		-- 1.3.6.1.4.1.34774.4.1.21.14.1.6
		hwPerfFileSystemAvRdOPSRspTime OBJECT-TYPE
			SYNTAX Counter64
			MAX-ACCESS read-only
			STATUS current
			DESCRIPTION
				"Average read OPS response time of the file system (unit: μs)."
			::= { hwPerfFileSystemEntry 6 }

		
		-- 1.3.6.1.4.1.34774.4.1.21.14.1.7
		hwPerfFileSystemAvWrOPSRspTime OBJECT-TYPE
			SYNTAX Counter64
			MAX-ACCESS read-only
			STATUS current
			DESCRIPTION
				"Average write OPS response time of the file system (unit: μs)."
			::= { hwPerfFileSystemEntry 7 }

		
		-- 1.3.6.1.4.1.34774.4.1.21.14.1.8
		hwPerfFileSystemWriteOPS OBJECT-TYPE
			SYNTAX Counter64
			MAX-ACCESS read-only
			STATUS current
			DESCRIPTION
				"Write OPS of the file system."
			::= { hwPerfFileSystemEntry 8 }

		
		-- 1.3.6.1.4.1.34774.4.1.21.14.1.9
		hwPerfFileSystemWriteBandwidth OBJECT-TYPE
			SYNTAX Counter64
			MAX-ACCESS read-only
			STATUS current
			DESCRIPTION
				"Write bandwidth of the file system (unit: MB/s)."
			::= { hwPerfFileSystemEntry 9 }

		
		-- 1.3.6.1.4.1.34774.4.1.21.15
		hwPerfControllerNFSV41Table OBJECT-TYPE
			SYNTAX SEQUENCE OF HwPerfControllerNFSV41Entry
			MAX-ACCESS not-accessible
			STATUS current
			DESCRIPTION
				"This table is used to query the NFSv41 performance data of controllers."
			::= { hwPerformance 15 }

		
		-- 1.3.6.1.4.1.34774.4.1.21.15.1
		hwPerfControllerNFSV41Entry OBJECT-TYPE
			SYNTAX HwPerfControllerNFSV41Entry
			MAX-ACCESS not-accessible
			STATUS current
			DESCRIPTION
				"A table containing the part component."
			INDEX { hwPerfControllerNFSV41ID }
			::= { hwPerfControllerNFSV41Table 1 }

		
		HwPerfControllerNFSV41Entry ::=
			SEQUENCE { 
				hwPerfControllerNFSV41ID
					OCTET STRING,
				hwPerfControllerNFSV41OPS
					Counter64,
				hwPerfControllerNFSV41Bps
					Counter64
			 }

		-- 1.3.6.1.4.1.34774.4.1.21.15.1.1
		hwPerfControllerNFSV41ID OBJECT-TYPE
			SYNTAX OCTET STRING
			MAX-ACCESS read-only
			STATUS current
			DESCRIPTION
				"Controller ID."
			::= { hwPerfControllerNFSV41Entry 1 }

		
		-- 1.3.6.1.4.1.34774.4.1.21.15.1.2
		hwPerfControllerNFSV41OPS OBJECT-TYPE
			SYNTAX Counter64
			MAX-ACCESS read-only
			STATUS current
			DESCRIPTION
				"NFSv4 OPS of the controller."
			::= { hwPerfControllerNFSV41Entry 2 }

		
		-- 1.3.6.1.4.1.34774.4.1.21.15.1.3
		hwPerfControllerNFSV41Bps OBJECT-TYPE
			SYNTAX Counter64
			MAX-ACCESS read-only
			STATUS current
			DESCRIPTION
				"NFSv4 throughput of the controller (unit: byte/s)."
			::= { hwPerfControllerNFSV41Entry 3 }

		
		-- 1.6
		isoConformance OBJECT IDENTIFIER ::= { iso 6 }

		
		-- 1.6.1
		isoGroups OBJECT IDENTIFIER ::= { isoConformance 1 }

		
		-- 1.6.1.1
		currentObjectGroup OBJECT-GROUP
			OBJECTS { hwPerfControllerNFSV3ID, hwPerfControllerNFSV4ID, hwPerfControllerSMBV1ID, hwPerfControllerSMBV2ID, hwPerfFileSystemID, 
				hwPerfNodeCPUUsage, hwPerfNodeAvgCacheUsage, hwPerfLunTotalIOPS, hwPerfLunHitRate, hwPerfLunReadIOPS, 
				hwPerfLunWriteIOPS, hwPerfLunTotalTraffic, hwPerfLunReadTraffic, hwPerfLunWriteTraffic, hwPerfPortDelay, 
				hwPerfPortTotalIOPS, hwPerfPortReadIOPS, hwPerfPortWriteIOPS, hwPerfPortTotalTraffic, hwPerfPortReadTraffic, 
				hwPerfPortWriteTraffic, hwPerfNodeDelay, hwPerfNodeTotalIOPS, hwPerfNodeReadIOPS, hwPerfNodeWriteIOPS, 
				hwPerfNodeTotalTraffic, hwPerfNodeReadTraffic, hwPerfNodeWriteTraffic, hwPerfLunID, hwPerfPortIfIndex, 
				hwPerfLunWriteIORate, hwPerfLunReadIORate, hwPerfCacheID, hwPerfCacheReadUtilization, hwPerfCacheWriteUtilization, 
				hwPerfCacheMirrorWriteUtilization, hwPerfCacheHitRatio, hwPerfLunMaxTraffic, hwPerfLunMaxIOPS, hwPerfPortMaxTraffic, 
				hwPerfPortMaxIOPS, hwPerfNodeFileBandwidth, hwPerfNodeFileOPS, hwPerfControllerNFSV3Bps, hwPerfControllerNFSV3OPS, 
				hwPerfControllerNFSV4OPS, hwPerfControllerNFSV4Bps, hwPerfControllerSMBV1OPS, hwPerfControllerSMBV2OPS, hwPerfControllerSMBV2Bps, 
				hwPerfFileSystemOPS, hwPerfFileSystemServiceTime, hwPerfFileSystemReadOPS, hwPerfFileSystemReadBandwidth, hwPerfFileSystemWriteOPS, 
				hwPerfFileSystemWriteBandwidth, hwPerformanceSwitch, hwPerfFileSystemAvRdOPSRspTime, hwPerfFileSystemAvWrOPSRspTime, hwPerfPortLocation, 
				hwPerfLunAverageIOResponseTime, hwPerfLunMaxIOResponseTime, hwPerfLunAverageReadIOLatency, hwPerfLunAverageWriteIOLatency, hwPerfControllerNFSV41ID, 
				hwPerfControllerNFSV41OPS, hwPerfControllerNFSV41Bps, hwPerfControllerSMBV1Bps, hwPerfNodeIfIndex }
			STATUS current
			DESCRIPTION 
				"Enter the description of the created OBJECT-GROUP."
			::= { isoGroups 1 }

		
		-- 1.6.2
		isoCompliances OBJECT IDENTIFIER ::= { isoConformance 2 }

		
--   this module
-- this module
		-- 1.6.2.1
		basicCompliance MODULE-COMPLIANCE
			STATUS current
			DESCRIPTION 
				"Enter the description of the created MODULE-COMPLIANCE."
			MODULE -- this module
				MANDATORY-GROUPS { currentObjectGroup }
			::= { isoCompliances 1 }

		
	
	END

--
-- ISM-PERFORMANCE-MIB.mib
--
